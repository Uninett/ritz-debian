-- *****************************************************************
-- CISCO-TC.my:  Cisco MIB Textual Conventions
--
-- May 1994, Jeffrey T. Johnson
--
-- Copyright (c) 1994-1997 by cisco Systems, Inc.
-- All rights reserved.
-- 
-- *****************************************************************
--

CISCO-TC DEFINITIONS ::= BEGIN

IMPORTS
	MODULE-IDENTITY,
	Gauge32,
	Integer32
		FROM SNMPv2-SMI
	TEXTUAL-CONVENTION
		FROM SNMPv2-TC
	ciscoModules,
	ciscoProducts
		FROM CISCO-SMI;


ciscoTextualConventions MODULE-IDENTITY
	LAST-UPDATED	"9703130000Z"
	ORGANIZATION	"Cisco Systems, Inc."
	CONTACT-INFO
		"       Cisco Systems
			Customer Service

		Postal: 170 W Tasman Drive
			San Jose, CA  95134
			USA

		   Tel: +1 800 553-NETS

		E-mail: cs-snmp@cisco.com"
	DESCRIPTION
		"This module defines textual conventions used throughout
		cisco enterprise mibs."
        REVISION        "9703130000Z"
        DESCRIPTION
                "Added SAPType textual convention."
        REVISION        "9608140000Z"
        DESCRIPTION
                "Added InterfaceIndexOrZero textual convention."
        REVISION        "9607080000Z"
        DESCRIPTION
                "Added new CiscoNetworkProtocol enumerations."
        REVISION        "9602220000Z"
        DESCRIPTION
                "Added Unsigned32 textual conventions."
	REVISION	"9506070000Z"
	DESCRIPTION
		"Miscellaneous updates/corrections, including making
		CiscoNetworkProtocol enumerations contiguous."
	::= { ciscoModules 1 }


CiscoNetworkProtocol ::= TEXTUAL-CONVENTION
	STATUS		current
	DESCRIPTION
		"Represents the different types of network layer protocols."
	-- internal note: enumerations must match those in address.h
	SYNTAX		INTEGER {
				ip (1),
				decnet (2),
				pup (3),
				chaos (4),
				xns (5),
				x121 (6),
				appletalk (7),
				clns (8),
				lat (9),
				vines (10),
				cons (11),
				apollo (12),
				stun (13),
				novell (14),
				qllc (15),
				snapshot (16),
				atmIlmi (17),
				bstun (18),
				x25pvc (19),
				unknown (65535)
			}

CiscoNetworkAddress ::= TEXTUAL-CONVENTION
	DISPLAY-HINT	"1x:"
	STATUS		current
	DESCRIPTION
		"Represents a network layer address.  The length and format of
		the address is protocol dependent as follows:
		ip		4 octets
		decnet		2 octets
		pup		obsolete
		chaos		2 octets
		xns		10 octets
				first 4 octets are the net number
				last 6 octets are the host number
		x121	
		appletalk	3 octets
				first 2 octets are the net number
				last octet is the host number
		clns
		lat
		vines		6 octets
				first 4 octets are the net number
				last 2 octets are the host number
		cons
		apollo		10 octets
				first 4 octets are the net number
				last 6 octets are the host number
		stun 		8 octets
		novell		10 octets
				first 4 octets are the net number
				last 6 octets are the host number
		qllc		6 octets
		bstun		1 octet - bi-sync serial tunnel 
		snapshot	1 octet
		atmIlmi		4 octets
		x25 pvc		2 octets (12 bits)
		"
	SYNTAX		OCTET STRING

Unsigned32 ::= TEXTUAL-CONVENTION
        STATUS          current
        DESCRIPTION
                "An unsigned 32-bit quantity indistinguishable from Gauge32."
        SYNTAX          Gauge32

InterfaceIndexOrZero ::= TEXTUAL-CONVENTION
    DISPLAY-HINT "d"
    STATUS       current
    DESCRIPTION
            "Either the value 0, or the ifIndex value of an
            interface in the ifTable."
    SYNTAX       Integer32 (0..2147483647)

SAPType ::= TEXTUAL-CONVENTION
        DISPLAY-HINT "1x:"
        STATUS          current
        DESCRIPTION
          "Service Access Point - is a term that denotes the means
           by which a user entity in layer n+1 accesses a service
           of a provider entity in layer n."
        SYNTAX          Integer32 (0..254)
 
 
END
