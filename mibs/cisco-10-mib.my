--
-- Copyright (c) 1994 by cisco Systems, Inc.
-- All rights reserved.
-- 
--------------------------------------------------------------------
--

          -- Request for Comments: Draft             cisco Systems, Inc.


                                  -- cisco MIB*

                           -- Thu Mar 10 14:58:19 1994


                              -- cisco Systems, Inc.
                                 -- 1525 O'Brien
                             -- Menlo Park, CA  94025

                          -- customer-service@cisco.com



          -- 1. Introduction

          -- This memo describes the variables that are implemented for
          -- the cisco Systems, Inc.  set of products including the
          -- Gateway Server, Terminal Server, Trouter, and Protocol
          -- Translator.  The document relies upon the Structure of
          -- Management Information (SMI), RFC1155.  It is presented in
          -- a format described in RFC1212, the Concise MIB document.

          -- This  document describes the cisco local Management
          -- Information Base (MIB) variables for
          -- version 10.0 of the system software.


          -- 2. Object Definitions

               CISCO-MIB { iso org(3) dod(6) internet(1) private(4)
                                       enterprises(1) 9 }

               DEFINITIONS ::= BEGIN

               IMPORTS
                    enterprises, IpAddress, Counter, TimeTicks
                    FROM RFC1155-SMI
                    OBJECT-TYPE
                    FROM RFC-1212
                    ifIndex, ipAdEntAddr, ipRouteDest, tcpConnLocalAddress,
                    tcpConnLocalPort, tcpConnRemAddress, tcpConnRemPort,
                    DisplayString
                    FROM RFC1213-MIB;
          






          -- cisco MIB                                          [Page 1]
--





          -- Request for Comments: Draft             cisco Systems, Inc.


               cisco               OBJECT IDENTIFIER ::= { enterprises 9 }

               ciscoProducts       OBJECT IDENTIFIER ::= { cisco 1 }
               local               OBJECT IDENTIFIER ::= { cisco 2 }
               temporary           OBJECT IDENTIFIER ::= { cisco 3 }

               gateway-server      OBJECT IDENTIFIER ::= { ciscoProducts 1 }
               terminal-server     OBJECT IDENTIFIER ::= { ciscoProducts 2 }
               trouter             OBJECT IDENTIFIER ::= { ciscoProducts 3 }
               protocol-translator OBJECT IDENTIFIER ::= { ciscoProducts 4 }
               igs-sysID           OBJECT IDENTIFIER ::= { ciscoProducts 5 }
               c3000-sysID         OBJECT IDENTIFIER ::= { ciscoProducts 6 }
               c4000-sysID         OBJECT IDENTIFIER ::= { ciscoProducts 7 }
               c7000-sysID         OBJECT IDENTIFIER ::= { ciscoProducts 8 }
               cs-500-sysID        OBJECT IDENTIFIER ::= { ciscoProducts 9 }
               c2000-sysID         OBJECT IDENTIFIER ::= { ciscoProducts 10 }
               agsplus-sysID       OBJECT IDENTIFIER ::= { ciscoProducts 11 }
               c7010-sysID         OBJECT IDENTIFIER ::= { ciscoProducts 12 }
               c2500-sysID         OBJECT IDENTIFIER ::= { ciscoProducts 13 }
               c4500-sysID         OBJECT IDENTIFIER ::= { ciscoProducts 14 }

               lsystem             OBJECT IDENTIFIER ::= { local 1 }
               linterfaces         OBJECT IDENTIFIER ::= { local 2 }
               lat                 OBJECT IDENTIFIER ::= { local 3 }
               lip                 OBJECT IDENTIFIER ::= { local 4 }
               licmp               OBJECT IDENTIFIER ::= { local 5 }
               ltcp                OBJECT IDENTIFIER ::= { local 6 }
               ludp                OBJECT IDENTIFIER ::= { local 7 }
               legp                OBJECT IDENTIFIER ::= { local 8 }
               lts                 OBJECT IDENTIFIER ::= { local 9 }
               lflash              OBJECT IDENTIFIER ::= { local 10 }

               tmpdecnet           OBJECT IDENTIFIER ::= { temporary 1 }
               tmpxns              OBJECT IDENTIFIER ::= { temporary 2 }
               tmpappletalk        OBJECT IDENTIFIER ::= { temporary 3 }
               tmpnovell           OBJECT IDENTIFIER ::= { temporary 4 }
               tmpvines            OBJECT IDENTIFIER ::= { temporary 5 }
               tmpchassis          OBJECT IDENTIFIER ::= { temporary 6 }



          -- Product Section

          -- The product section contains the different product's
          -- object identifiers.  Each product has a unique object
          -- identifier allocated from this section which is referenced
          -- by the sysObjectID variable from RFC1156.






          -- cisco MIB                                          [Page 2]
--





          -- Request for Comments: Draft             cisco Systems, Inc.


               -- gateway-server      OBJECT IDENTIFIER ::= { products 1 }
               -- terminal-server     OBJECT IDENTIFIER ::= { products 2 }
               -- trouter             OBJECT IDENTIFIER ::= { products 3 }
               -- protocol-translator OBJECT IDENTIFIER ::= { products 4 }

               -- Beginning with 9.21 sysObjectID returns platform based IDs

               -- igs-sysID           OBJECT IDENTIFIER ::= { products 5 }
               -- c3000-sysID         OBJECT IDENTIFIER ::= { products 6 }
               -- c4000-sysID         OBJECT IDENTIFIER ::= { products 7 }
               -- c7000-sysID         OBJECT IDENTIFIER ::= { products 8 }
               -- cs-500-sysID        OBJECT IDENTIFIER ::= { products 9 }
               -- c2000-sysID         OBJECT IDENTIFIER ::= { products 10 }
               -- agsplus-sysID       OBJECT IDENTIFIER ::= { products 11 }

          -- New products will be added at the end of this list.


          -- Local Variable Section

          -- This section describes the local variables within the cisco
          -- product line.  Groups may or may not be present depending
          -- on the software options present in the managed device.


          -- Local System Group

          -- This group is present in all products.

               romId OBJECT-TYPE
                   SYNTAX  DisplayString
                   ACCESS  read-only
                   STATUS  mandatory
                   DESCRIPTION
                           "This variable contains a printable octet
                           string which contains the System Bootstrap
                           description and version identification."
                   ::= { lsystem 1 }

               whyReload OBJECT-TYPE
                   SYNTAX  DisplayString
                   ACCESS  read-only
                   STATUS  mandatory
                   DESCRIPTION
                           "This variable contains a printable octet





          -- cisco MIB                                          [Page 3]
--





          -- Request for Comments: Draft             cisco Systems, Inc.


                           string which contains the reason why the
                           system was last restarted."
                   ::= { lsystem 2 }

               hostName OBJECT-TYPE
                   SYNTAX  DisplayString
                   ACCESS  read-only
                   STATUS  mandatory
                   DESCRIPTION
                           "This variable represents the name of the
                           host in printable ascii characters."
                   ::= { lsystem 3 }

               domainName OBJECT-TYPE
                   SYNTAX  DisplayString
                   ACCESS  read-only
                   STATUS  mandatory
                   DESCRIPTION
                           "This variable is the domain portion of the
                           domain name of the host."
                   ::= { lsystem 4 }

               authAddr OBJECT-TYPE
                   SYNTAX  IpAddress
                   ACCESS  read-only
                   STATUS  mandatory
                   DESCRIPTION
                           "This variable contains the last SNMP
                           authorization failure IP address."
                   ::= { lsystem 5 }

               bootHost OBJECT-TYPE
                   SYNTAX  IpAddress
                   ACCESS  read-only
                   STATUS  mandatory
                   DESCRIPTION
                           "Contains the IP address of the host that
                           supplied the currently running software."
                   ::= { lsystem 6 }

               ping OBJECT-TYPE
                   SYNTAX  INTEGER
                   ACCESS  read-write
                   STATUS  mandatory
                   DESCRIPTION





          -- cisco MIB                                          [Page 4]
--





          -- Request for Comments: Draft             cisco Systems, Inc.


                           "Supplies a way to ping a host from this
                           entity. The ping variable takes the following
                           instance identifiers: 1 - IP protocol ping.
                           IP - address to ping. integer - count of
                           packets to send. integer - size of ping
                           packet. integer - timeout delay between
                           packets."
                   ::= { lsystem 7 }

               freeMem OBJECT-TYPE
                   SYNTAX  INTEGER
                   ACCESS  read-only
                   STATUS  mandatory
                   DESCRIPTION
                           "Return the amount of free memory in bytes."
                   ::= { lsystem 8 }

               bufferElFree OBJECT-TYPE
                   SYNTAX  INTEGER
                   ACCESS  read-only
                   STATUS  mandatory
                   DESCRIPTION
                           "Contains the number of free buffer
                           elements."
                   ::= { lsystem 9 }

               bufferElMax OBJECT-TYPE
                   SYNTAX  INTEGER
                   ACCESS  read-only
                   STATUS  mandatory
                   DESCRIPTION
                           "Contains the maximum number of buffer
                           elements."
                   ::= { lsystem 10 }

               bufferElHit OBJECT-TYPE
                   SYNTAX  INTEGER
                   ACCESS  read-only
                   STATUS  mandatory
                   DESCRIPTION
                           "Contains the number of buffer element hits."
                   ::= { lsystem 11 }

               bufferElMiss OBJECT-TYPE
                   SYNTAX  INTEGER





          -- cisco MIB                                          [Page 5]
--





          -- Request for Comments: Draft             cisco Systems, Inc.


                   ACCESS  read-only
                   STATUS  mandatory
                   DESCRIPTION
                           "Contains the number of buffer element
                           misses."
                   ::= { lsystem 12 }

               bufferElCreate OBJECT-TYPE
                   SYNTAX  INTEGER
                   ACCESS  read-only
                   STATUS  mandatory
                   DESCRIPTION
                           "Contains the number of buffer element
                           creates."
                   ::= { lsystem 13 }

               bufferSmSize OBJECT-TYPE
                   SYNTAX  INTEGER
                   ACCESS  read-only
                   STATUS  mandatory
                   DESCRIPTION
                           "Contains the size of small buffers."
                   ::= { lsystem 14 }

               bufferSmTotal OBJECT-TYPE
                   SYNTAX  INTEGER
                   ACCESS  read-only
                   STATUS  mandatory
                   DESCRIPTION
                           "Contains the total number of small buffers."
                   ::= { lsystem 15 }

               bufferSmFree OBJECT-TYPE
                   SYNTAX  INTEGER
                   ACCESS  read-only
                   STATUS  mandatory
                   DESCRIPTION
                           "Contains the number of free small buffers."
                   ::= { lsystem 16 }

               bufferSmMax OBJECT-TYPE
                   SYNTAX  INTEGER
                   ACCESS  read-only
                   STATUS  mandatory
                   DESCRIPTION





          -- cisco MIB                                          [Page 6]
--





          -- Request for Comments: Draft             cisco Systems, Inc.


                           "Contains the maximum number of small
                           buffers."
                   ::= { lsystem 17 }

               bufferSmHit OBJECT-TYPE
                   SYNTAX  INTEGER
                   ACCESS  read-only
                   STATUS  mandatory
                   DESCRIPTION
                           "Contains the number of small buffer hits."
                   ::= { lsystem 18 }

               bufferSmMiss OBJECT-TYPE
                   SYNTAX  INTEGER
                   ACCESS  read-only
                   STATUS  mandatory
                   DESCRIPTION
                           "Contains the number of small buffer misses."
                   ::= { lsystem 19 }

               bufferSmTrim OBJECT-TYPE
                   SYNTAX  INTEGER
                   ACCESS  read-only
                   STATUS  mandatory
                   DESCRIPTION
                           "Contains the number of small buffer trims."
                   ::= { lsystem 20 }

               bufferSmCreate OBJECT-TYPE
                   SYNTAX  INTEGER
                   ACCESS  read-only
                   STATUS  mandatory
                   DESCRIPTION
                           "Contains the number of small buffer
                           creates."
                   ::= { lsystem 21 }

               bufferMdSize OBJECT-TYPE
                   SYNTAX  INTEGER
                   ACCESS  read-only
                   STATUS  mandatory
                   DESCRIPTION
                           "Contains the size of medium buffers."
                   ::= { lsystem 22 }






          -- cisco MIB                                          [Page 7]
--





          -- Request for Comments: Draft             cisco Systems, Inc.


               bufferMdTotal OBJECT-TYPE
                   SYNTAX  INTEGER
                   ACCESS  read-only
                   STATUS  mandatory
                   DESCRIPTION
                           "Contains the total number of medium
                           buffers."
                   ::= { lsystem 23 }

               bufferMdFree OBJECT-TYPE
                   SYNTAX  INTEGER
                   ACCESS  read-only
                   STATUS  mandatory
                   DESCRIPTION
                           "Contains the number of free medium buffers."
                   ::= { lsystem 24 }

               bufferMdMax OBJECT-TYPE
                   SYNTAX  INTEGER
                   ACCESS  read-only
                   STATUS  mandatory
                   DESCRIPTION
                           "Contains the maximum number of medium
                           buffers."
                   ::= { lsystem 25 }

               bufferMdHit OBJECT-TYPE
                   SYNTAX  INTEGER
                   ACCESS  read-only
                   STATUS  mandatory
                   DESCRIPTION
                           "Contains the number of medium buffer hits."
                   ::= { lsystem 26 }

               bufferMdMiss OBJECT-TYPE
                   SYNTAX  INTEGER
                   ACCESS  read-only
                   STATUS  mandatory
                   DESCRIPTION
                           "Contains the number of medium buffer
                           misses."
                   ::= { lsystem 27 }

               bufferMdTrim OBJECT-TYPE
                   SYNTAX  INTEGER





          -- cisco MIB                                          [Page 8]
--





          -- Request for Comments: Draft             cisco Systems, Inc.


                   ACCESS  read-only
                   STATUS  mandatory
                   DESCRIPTION
                           "Contains the number of medium buffer trims."
                   ::= { lsystem 28 }

               bufferMdCreate OBJECT-TYPE
                   SYNTAX  INTEGER
                   ACCESS  read-only
                   STATUS  mandatory
                   DESCRIPTION
                           "Contains the number of medium buffer
                           creates."
                   ::= { lsystem 29 }

               bufferBgSize OBJECT-TYPE
                   SYNTAX  INTEGER
                   ACCESS  read-only
                   STATUS  mandatory
                   DESCRIPTION
                           "Contains the size of big buffers."
                   ::= { lsystem 30 }

               bufferBgTotal OBJECT-TYPE
                   SYNTAX  INTEGER
                   ACCESS  read-only
                   STATUS  mandatory
                   DESCRIPTION
                           "Contains the total number of big buffers."
                   ::= { lsystem 31 }

               bufferBgFree OBJECT-TYPE
                   SYNTAX  INTEGER
                   ACCESS  read-only
                   STATUS  mandatory
                   DESCRIPTION
                           "Contains the number of free big buffers."
                   ::= { lsystem 32 }

               bufferBgMax OBJECT-TYPE
                   SYNTAX  INTEGER
                   ACCESS  read-only
                   STATUS  mandatory
                   DESCRIPTION
                           "Contains the maximum number of big buffers."





          -- cisco MIB                                          [Page 9]
--





          -- Request for Comments: Draft             cisco Systems, Inc.


                   ::= { lsystem 33 }

               bufferBgHit OBJECT-TYPE
                   SYNTAX  INTEGER
                   ACCESS  read-only
                   STATUS  mandatory
                   DESCRIPTION
                           "Contains the number of big buffer hits."
                   ::= { lsystem 34 }

               bufferBgMiss OBJECT-TYPE
                   SYNTAX  INTEGER
                   ACCESS  read-only
                   STATUS  mandatory
                   DESCRIPTION
                           "Contains the number of big buffer misses."
                   ::= { lsystem 35 }

               bufferBgTrim OBJECT-TYPE
                   SYNTAX  INTEGER
                   ACCESS  read-only
                   STATUS  mandatory
                   DESCRIPTION
                           "Contains the number of big buffer trims."
                   ::= { lsystem 36 }

               bufferBgCreate OBJECT-TYPE
                   SYNTAX  INTEGER
                   ACCESS  read-only
                   STATUS  mandatory
                   DESCRIPTION
                           "Contains the number of big buffer creates."
                   ::= { lsystem 37 }

               bufferLgSize OBJECT-TYPE
                   SYNTAX  INTEGER
                   ACCESS  read-only
                   STATUS  mandatory
                   DESCRIPTION
                           "Contains the size of large buffers."
                   ::= { lsystem 38 }

               bufferLgTotal OBJECT-TYPE
                   SYNTAX  INTEGER
                   ACCESS  read-only





          -- cisco MIB                                         [Page 10]
--





          -- Request for Comments: Draft             cisco Systems, Inc.


                   STATUS  mandatory
                   DESCRIPTION
                           "Contains the total number of large buffers."
                   ::= { lsystem 39 }

               bufferLgFree OBJECT-TYPE
                   SYNTAX  INTEGER
                   ACCESS  read-only
                   STATUS  mandatory
                   DESCRIPTION
                           "Contains the number of free large buffers."
                   ::= { lsystem 40 }

               bufferLgMax OBJECT-TYPE
                   SYNTAX  INTEGER
                   ACCESS  read-only
                   STATUS  mandatory
                   DESCRIPTION
                           "Contains the maximum number of large
                           buffers."
                   ::= { lsystem 41 }

               bufferLgHit OBJECT-TYPE
                   SYNTAX  INTEGER
                   ACCESS  read-only
                   STATUS  mandatory
                   DESCRIPTION
                           "Contains the number of large buffer hits."
                   ::= { lsystem 42 }

               bufferLgMiss OBJECT-TYPE
                   SYNTAX  INTEGER
                   ACCESS  read-only
                   STATUS  mandatory
                   DESCRIPTION
                           "Contains the number of large buffer misses."
                   ::= { lsystem 43 }

               bufferLgTrim OBJECT-TYPE
                   SYNTAX  INTEGER
                   ACCESS  read-only
                   STATUS  mandatory
                   DESCRIPTION
                           "Contains the number of large buffer trims."
                   ::= { lsystem 44 }





          -- cisco MIB                                         [Page 11]
--





          -- Request for Comments: Draft             cisco Systems, Inc.


               bufferLgCreate OBJECT-TYPE
                   SYNTAX  INTEGER
                   ACCESS  read-only
                   STATUS  mandatory
                   DESCRIPTION
                           "Contains the number of large buffer
                           creates."
                   ::= { lsystem 45 }

               bufferFail OBJECT-TYPE
                   SYNTAX  INTEGER
                   ACCESS  read-only
                   STATUS  mandatory
                   DESCRIPTION
                           "Count of the number of buffer allocation
                           failures."
                   ::= { lsystem 46 }

               bufferNoMem OBJECT-TYPE
                   SYNTAX  INTEGER
                   ACCESS  read-only
                   STATUS  mandatory
                   DESCRIPTION
                           "Count of the number of buffer create
                           failures due to no free memory."
                   ::= { lsystem 47 }

               netConfigAddr OBJECT-TYPE
                   SYNTAX  IpAddress
                   ACCESS  read-only
                   STATUS  mandatory
                   DESCRIPTION
                           "Holds the address of the host that supplied
                           the network-confg file."
                   ::= { lsystem 48 }

               netConfigName OBJECT-TYPE
                   SYNTAX  DisplayString
                   ACCESS  read-only
                   STATUS  mandatory
                   DESCRIPTION
                           "Holds the name of the network configuration
                           file."
                   ::= { lsystem 49 }






          -- cisco MIB                                         [Page 12]
--





          -- Request for Comments: Draft             cisco Systems, Inc.


               netConfigSet OBJECT-TYPE
                   SYNTAX  DisplayString
                   ACCESS  write-only
                   STATUS  mandatory
                   DESCRIPTION
                           "Permit the loading of a new network-confg
                           file using TFTP."
                   ::= { lsystem 50 }

               hostConfigAddr OBJECT-TYPE
                   SYNTAX  IpAddress
                   ACCESS  read-only
                   STATUS  mandatory
                   DESCRIPTION
                           "Contains the address of the host that
                           provided the host-config file."
                   ::= { lsystem 51 }

               hostConfigName OBJECT-TYPE
                   SYNTAX  DisplayString
                   ACCESS  read-only
                   STATUS  mandatory
                   DESCRIPTION
                           "Contains the name of the last configured
                           host-confg file."
                   ::= { lsystem 52 }

               hostConfigSet OBJECT-TYPE
                   SYNTAX  DisplayString
                   ACCESS  write-only
                   STATUS  mandatory
                   DESCRIPTION
                           "Permit the loading of a new host-confg file
                           using TFTP."
                   ::= { lsystem 53 }

               writeMem OBJECT-TYPE
                   SYNTAX  INTEGER
                   ACCESS  write-only
                   STATUS  mandatory
                   DESCRIPTION
                           "Write configuration into non-volatile memory
                           / erase config memory if 0."
                   ::= { lsystem 54 }






          -- cisco MIB                                         [Page 13]
--





          -- Request for Comments: Draft             cisco Systems, Inc.


               writeNet OBJECT-TYPE
                   SYNTAX  DisplayString
                   ACCESS  write-only
                   STATUS  mandatory
                   DESCRIPTION
                           "Write configuration to host using TFTP."
                   ::= { lsystem 55 }

               busyPer OBJECT-TYPE
                   SYNTAX  INTEGER
                   ACCESS  read-only
                   STATUS  mandatory
                   DESCRIPTION
                           "CPU busy percentage in the last 5 second
                           period. Not the last 5 realtime seconds but
                           the last 5 second period in the scheduler."
                   ::= { lsystem 56 }

               avgBusy1 OBJECT-TYPE
                   SYNTAX  INTEGER
                   ACCESS  read-only
                   STATUS  mandatory
                   DESCRIPTION
                           "1 minute exponentially-decayed moving
                           average of the CPU busy percentage."
                   ::= { lsystem 57 }

               avgBusy5 OBJECT-TYPE
                   SYNTAX  INTEGER
                   ACCESS  read-only
                   STATUS  mandatory
                   DESCRIPTION
                           "5 minute exponentially-decayed moving
                           average of the CPU busy percentage."
                   ::= { lsystem 58 }

               idleCount OBJECT-TYPE
                   SYNTAX  INTEGER
                   ACCESS  read-write
                   STATUS  mandatory
                   DESCRIPTION
                           "cisco internal variable. not to be used"
                   ::= { lsystem 59 }

               idleWired OBJECT-TYPE





          -- cisco MIB                                         [Page 14]
--





          -- Request for Comments: Draft             cisco Systems, Inc.


                   SYNTAX  INTEGER
                   ACCESS  read-write
                   STATUS  mandatory
                   DESCRIPTION
                           "cisco internal variable. not to be used"
                   ::= { lsystem 60 }

               ciscoContactInfo OBJECT-TYPE
                   SYNTAX  DisplayString
                   ACCESS  read-only
                   STATUS  mandatory
                   DESCRIPTION
                           "cisco's name and address"
                   ::= { lsystem 61 }

               bufferHgSize OBJECT-TYPE
                   SYNTAX  INTEGER
                   ACCESS  read-only
                   STATUS  mandatory
                   DESCRIPTION
                           "Contains the size of huge buffers."
                   ::= { lsystem 62 }

               bufferHgTotal OBJECT-TYPE
                   SYNTAX  INTEGER
                   ACCESS  read-only
                   STATUS  mandatory
                   DESCRIPTION
                           "Contains the total number of huge buffers."
                   ::= { lsystem 63 }

               bufferHgFree OBJECT-TYPE
                   SYNTAX  INTEGER
                   ACCESS  read-only
                   STATUS  mandatory
                   DESCRIPTION
                           "Contains the number of free huge buffers."
                   ::= { lsystem 64 }

               bufferHgMax OBJECT-TYPE
                   SYNTAX  INTEGER
                   ACCESS  read-only
                   STATUS  mandatory
                   DESCRIPTION
                           "Contains the maximum number of huge





          -- cisco MIB                                         [Page 15]
--





          -- Request for Comments: Draft             cisco Systems, Inc.


                           buffers."
                   ::= { lsystem 65 }

               bufferHgHit OBJECT-TYPE
                   SYNTAX  INTEGER
                   ACCESS  read-only
                   STATUS  mandatory
                   DESCRIPTION
                           "Contains the number of huge buffer hits."
                   ::= { lsystem 66 }

               bufferHgMiss OBJECT-TYPE
                   SYNTAX  INTEGER
                   ACCESS  read-only
                   STATUS  mandatory
                   DESCRIPTION
                           "Contains the number of huge buffer misses."
                   ::= { lsystem 67 }

               bufferHgTrim OBJECT-TYPE
                   SYNTAX  INTEGER
                   ACCESS  read-only
                   STATUS  mandatory
                   DESCRIPTION
                           "Contains the number of huge buffer trims."
                   ::= { lsystem 68 }

               bufferHgCreate OBJECT-TYPE
                   SYNTAX  INTEGER
                   ACCESS  read-only
                   STATUS  mandatory
                   DESCRIPTION
                           "Contains the number of huge buffer creates."
                   ::= { lsystem 69 }

               netConfigProto OBJECT-TYPE
                   SYNTAX  INTEGER
                   ACCESS  read-only
                   STATUS  mandatory
                   DESCRIPTION
                           "Holds the protocol that supplied the
                           network-confg file."
                   ::= { lsystem 70 }

               hostConfigProto OBJECT-TYPE





          -- cisco MIB                                         [Page 16]
--





          -- Request for Comments: Draft             cisco Systems, Inc.


                   SYNTAX  INTEGER
                   ACCESS  read-only
                   STATUS  mandatory
                   DESCRIPTION
                           "Holds the protocol that supplied the host-
                           confg file."
                   ::= { lsystem 71 }

               sysConfigAddr OBJECT-TYPE
                   SYNTAX  IpAddress
                   ACCESS  read-only
                   STATUS  mandatory
                   DESCRIPTION
                           "Holds the address of the host that supplied
                           the system boot image."
                   ::= { lsystem 72 }

               sysConfigName OBJECT-TYPE
                   SYNTAX  DisplayString
                   ACCESS  read-only
                   STATUS  mandatory
                   DESCRIPTION
                           "Holds the name of the system boot image."
                   ::= { lsystem 73 }

               sysConfigProto OBJECT-TYPE
                   SYNTAX  INTEGER
                   ACCESS  read-only
                   STATUS  mandatory
                   DESCRIPTION
                           "Holds the protocol that supplied the system
                           boot image."
                   ::= { lsystem 74 }

               sysClearARP OBJECT-TYPE
                   SYNTAX  INTEGER
                   ACCESS  write-only
                   STATUS  mandatory
                   DESCRIPTION
                           "Perform a clearing of the entire ARP cache
                           and invalidation of route caches."
                   ::= { lsystem 75 }

               sysClearInt OBJECT-TYPE
                   SYNTAX  INTEGER





          -- cisco MIB                                         [Page 17]
--





          -- Request for Comments: Draft             cisco Systems, Inc.


                   ACCESS  write-only
                   STATUS  mandatory
                   DESCRIPTION
                           "Clear interface given IfIndex as value."
                   ::= { lsystem 76 }

               envPresent OBJECT-TYPE
                   SYNTAX  INTEGER
                   ACCESS  read-only
                   STATUS  mandatory
                   DESCRIPTION
                           "Is there an environmental monitor card in
                           this box?, 0 - No, 1-AGS card present, wrong
                           firmware, 2-AGS CARD present, firmware ok,
                           3-7000 support"
                   ::= { lsystem 77 }

               envTestPt1Descr OBJECT-TYPE
                   SYNTAX  DisplayString
                   ACCESS  read-only
                   STATUS  mandatory
                   DESCRIPTION
                           "Description of the test point 1. Typically
                           ambient air or the temperature of air
                           entering the router"
                   ::= { lsystem 78 }

               envTestPt1Measure OBJECT-TYPE
                   SYNTAX  INTEGER
                   ACCESS  read-only
                   STATUS  mandatory
                   DESCRIPTION
                           "Current value of test point 1. Typically a
                           temperature in centigrade."
                   ::= { lsystem 79 }

               envTestPt2Descr OBJECT-TYPE
                   SYNTAX  DisplayString
                   ACCESS  read-only
                   STATUS  mandatory
                   DESCRIPTION
                           "Description of the test point 2. Typically
                           airflow or the temperature of air leaving the
                           router"
                   ::= { lsystem 80 }





          -- cisco MIB                                         [Page 18]
--





          -- Request for Comments: Draft             cisco Systems, Inc.


               envTestPt2Measure OBJECT-TYPE
                   SYNTAX  INTEGER
                   ACCESS  read-only
                   STATUS  mandatory
                   DESCRIPTION
                           "Current value of test point 2. Typically a
                           temperature in centigrade."
                   ::= { lsystem 81 }

               envTestPt3Descr OBJECT-TYPE
                   SYNTAX  DisplayString
                   ACCESS  read-only
                   STATUS  mandatory
                   DESCRIPTION
                           "Description of the test point 3. Typically
                           +5 volt"
                   ::= { lsystem 82 }

               envTestPt3Measure OBJECT-TYPE
                   SYNTAX  INTEGER
                   ACCESS  read-only
                   STATUS  mandatory
                   DESCRIPTION
                           "Current value of test point 3. Typically the
                           value in millivolts of the +5v supply"
                   ::= { lsystem 83 }

               envTestPt4Descr OBJECT-TYPE
                   SYNTAX  DisplayString
                   ACCESS  read-only
                   STATUS  mandatory
                   DESCRIPTION
                           "Description of the test point 4. Typically
                           +12 volt"
                   ::= { lsystem 84 }

               envTestPt4Measure OBJECT-TYPE
                   SYNTAX  INTEGER
                   ACCESS  read-only
                   STATUS  mandatory
                   DESCRIPTION
                           "Current value of test point 4. Typically the
                           value in millivolts of the +12v supply"
                   ::= { lsystem 85 }






          -- cisco MIB                                         [Page 19]
--





          -- Request for Comments: Draft             cisco Systems, Inc.


               envTestPt5Descr OBJECT-TYPE
                   SYNTAX  DisplayString
                   ACCESS  read-only
                   STATUS  mandatory
                   DESCRIPTION
                           "Description of the test point 5. Typically
                           -12 volt"
                   ::= { lsystem 86 }

               envTestPt5Measure OBJECT-TYPE
                   SYNTAX  INTEGER
                   ACCESS  read-only
                   STATUS  mandatory
                   DESCRIPTION
                           "Current value of test point 5. Typically the
                           value in millivolts of the -12v supply"
                   ::= { lsystem 87 }

               envTestPt6Descr OBJECT-TYPE
                   SYNTAX  DisplayString
                   ACCESS  read-only
                   STATUS  mandatory
                   DESCRIPTION
                           "Description of the test point 6. Typically
                           -5 volt"
                   ::= { lsystem 88 }

               envTestPt6Measure OBJECT-TYPE
                   SYNTAX  INTEGER
                   ACCESS  read-only
                   STATUS  mandatory
                   DESCRIPTION
                           "Current value of test point 6. Typically the
                           value in millivolts of the -5v supply"
                   ::= { lsystem 89 }

               envTestPt1MarginVal OBJECT-TYPE
                   SYNTAX  INTEGER
                   ACCESS  read-only
                   STATUS  mandatory
                   DESCRIPTION
                           "Value at which the router will shutdown.
                           Typically the ambient air temperature that
                           will shut the router down. (e.g. 43)"
                   ::= { lsystem 90 }





          -- cisco MIB                                         [Page 20]
--





          -- Request for Comments: Draft             cisco Systems, Inc.


               envTestPt2MarginVal OBJECT-TYPE
                   SYNTAX  INTEGER
                   ACCESS  read-only
                   STATUS  mandatory
                   DESCRIPTION
                           "Value at which the router will shutdown.
                           Typically the airflow air temperature that
                           will shut the router down. (e.g. 58)"
                   ::= { lsystem 91 }

               envTestPt3MarginPercent OBJECT-TYPE
                   SYNTAX  INTEGER
                   ACCESS  read-only
                   STATUS  mandatory
                   DESCRIPTION
                           "+/- Percentage that will shut the router
                           down, (e.g. 10%) typically +5 volt"
                   ::= { lsystem 92 }

               envTestPt4MarginPercent OBJECT-TYPE
                   SYNTAX  INTEGER
                   ACCESS  read-only
                   STATUS  mandatory
                   DESCRIPTION
                           "+/- Percentage that will shut the router
                           down, (e.g. 15%) typically +12 volt"
                   ::= { lsystem 93 }

               envTestPt5MarginPercent OBJECT-TYPE
                   SYNTAX  INTEGER
                   ACCESS  read-only
                   STATUS  mandatory
                   DESCRIPTION
                           "+/- Percentage that will shut the router
                           down, (e.g. 15%) typically -12 volt"
                   ::= { lsystem 94 }

               envTestPt6MarginPercent OBJECT-TYPE
                   SYNTAX  INTEGER
                   ACCESS  read-only
                   STATUS  mandatory
                   DESCRIPTION
                           "+/- Percentage that will shut the router
                           down, (e.g. 10%) typically -5 volt"
                   ::= { lsystem 95 }





          -- cisco MIB                                         [Page 21]
--





          -- Request for Comments: Draft             cisco Systems, Inc.


               envTestPt1last OBJECT-TYPE
                   SYNTAX  INTEGER
                   ACCESS  read-only
                   STATUS  mandatory
                   DESCRIPTION
                           "Value of TestPt1 when last shutdown
                           occurred."
                   ::= { lsystem 96 }

               envTestPt2last OBJECT-TYPE
                   SYNTAX  INTEGER
                   ACCESS  read-only
                   STATUS  mandatory
                   DESCRIPTION
                           "Value of TestPt2 when last shutdown
                           occurred."
                   ::= { lsystem 97 }

               envTestPt3last OBJECT-TYPE
                   SYNTAX  INTEGER
                   ACCESS  read-only
                   STATUS  mandatory
                   DESCRIPTION
                           "Value of TestPt3 when last shutdown
                           occurred."
                   ::= { lsystem 98 }

               envTestPt4last OBJECT-TYPE
                   SYNTAX  INTEGER
                   ACCESS  read-only
                   STATUS  mandatory
                   DESCRIPTION
                           "Value of TestPt4 when last shutdown
                           occurred."
                   ::= { lsystem 99 }

               envTestPt5last OBJECT-TYPE
                   SYNTAX  INTEGER
                   ACCESS  read-only
                   STATUS  mandatory
                   DESCRIPTION
                           "Value of TestPt5 when last shutdown
                           occurred."
                   ::= { lsystem 100 }






          -- cisco MIB                                         [Page 22]
--





          -- Request for Comments: Draft             cisco Systems, Inc.


               envTestPt6last OBJECT-TYPE
                   SYNTAX  INTEGER
                   ACCESS  read-only
                   STATUS  mandatory
                   DESCRIPTION
                           "Value of TestPt6 when last shutdown
                           occurred."
                   ::= { lsystem 101 }

               envTestPt1warn OBJECT-TYPE
                   SYNTAX  INTEGER {
                        warning(1),
                        noWarning(2)
                   }
                   ACCESS  read-only
                   STATUS  mandatory
                   DESCRIPTION
                           "Is this test point at a warning level?"
                   ::= { lsystem 102 }

               envTestPt2warn OBJECT-TYPE
                   SYNTAX  INTEGER {
                        warning(1),
                        noWarning(2)
                   }
                   ACCESS  read-only
                   STATUS  mandatory
                   DESCRIPTION
                           "Is this test point at a warning level?"
                   ::= { lsystem 103 }

               envTestPt3warn OBJECT-TYPE
                   SYNTAX  INTEGER {
                        warning(1),
                        noWarning(2)
                   }
                   ACCESS  read-only
                   STATUS  mandatory
                   DESCRIPTION
                           "Is this test point at a warning level?"
                   ::= { lsystem 104 }

               envTestPt4warn OBJECT-TYPE
                   SYNTAX  INTEGER {
                        warning(1),





          -- cisco MIB                                         [Page 23]
--





          -- Request for Comments: Draft             cisco Systems, Inc.


                        noWarning(2)
                   }
                   ACCESS  read-only
                   STATUS  mandatory
                   DESCRIPTION
                           "Is this test point at a warning level?"
                   ::= { lsystem 105 }

               envTestPt5warn OBJECT-TYPE
                   SYNTAX  INTEGER {
                        warning(1),
                        noWarning(2)
                   }
                   ACCESS  read-only
                   STATUS  mandatory
                   DESCRIPTION
                           "Is this test point at a warning level?"
                   ::= { lsystem 106 }

               envTestPt6warn OBJECT-TYPE
                   SYNTAX  INTEGER {
                        warning(1),
                        noWarning(2)
                   }
                   ACCESS  read-only
                   STATUS  mandatory
                   DESCRIPTION
                           "Is this test point at a warning level?"
                   ::= { lsystem 107 }

               envFirmVersion OBJECT-TYPE
                   SYNTAX  DisplayString
                   ACCESS  read-only
                   STATUS  mandatory
                   DESCRIPTION
                           "Description of Environmental Card firmware"
                   ::= { lsystem 108 }

               envTechnicianID OBJECT-TYPE
                   SYNTAX  DisplayString
                   ACCESS  read-only
                   STATUS  mandatory
                   DESCRIPTION
                           "Technician ID"
                   ::= { lsystem 109 }





          -- cisco MIB                                         [Page 24]
--





          -- Request for Comments: Draft             cisco Systems, Inc.


               envType OBJECT-TYPE
                   SYNTAX  DisplayString
                   ACCESS  read-only
                   STATUS  mandatory
                   DESCRIPTION
                           "The type of environmental card"
                   ::= { lsystem 110 }

               envBurnDate OBJECT-TYPE
                   SYNTAX  DisplayString
                   ACCESS  read-only
                   STATUS  mandatory
                   DESCRIPTION
                           "The calibration / burn in date"
                   ::= { lsystem 111 }

               envSerialNumber OBJECT-TYPE
                   SYNTAX  DisplayString
                   ACCESS  read-only
                   STATUS  mandatory
                   DESCRIPTION
                           "Serial Number of environmental monitor card"
                   ::= { lsystem 112 }


               -- Local Interface Group

          -- This group is present in all products.


          -- Local Interface Table

          -- This group provides additional objects to the table
          -- defined by RFC1156.

               lifTable OBJECT-TYPE
                   SYNTAX  SEQUENCE OF LIfEntry
                   ACCESS  not-accessible
                   STATUS  mandatory
                   DESCRIPTION
                            "A list of interface entries."
                   ::= { linterfaces 1 }

               lifEntry OBJECT-TYPE
                   SYNTAX LIfEntry





          -- cisco MIB                                         [Page 25]
--





          -- Request for Comments: Draft             cisco Systems, Inc.


                   ACCESS  not-accessible
                   STATUS  mandatory
                   DESCRIPTION
                            "A collection of additional objects in the
                            cisco interface."
                   INDEX { ifIndex }
               ::= { lifTable 1 }

               LIfEntry ::=
                   SEQUENCE {
                       locIfHardType
                           DisplayString,
                       locIfLineProt
                           INTEGER,
                       locIfLastIn
                           INTEGER,
                       locIfLastOut
                           INTEGER,
                       locIfLastOutHang
                           INTEGER,
                       locIfInBitsSec
                           INTEGER,
                       locIfInPktsSec
                           INTEGER,
                       locIfOutBitsSec
                           INTEGER,
                       locIfOutPktsSec
                           INTEGER,
                       locIfInRunts
                           INTEGER,
                       locIfInGiants
                           INTEGER,
                       locIfInCRC
                           INTEGER,
                       locIfInFrame
                           INTEGER,
                       locIfInOverrun
                           INTEGER,
                       locIfInIgnored
                           INTEGER,
                       locIfInAbort
                           INTEGER,
                       locIfResets
                           INTEGER,
                       locIfRestarts





          -- cisco MIB                                         [Page 26]
--





          -- Request for Comments: Draft             cisco Systems, Inc.


                           INTEGER,
                       locIfKeep
                           INTEGER,
                       locIfReason
                           DisplayString,
                       locIfCarTrans
                           INTEGER,
                       locIfReliab
                           INTEGER,
                       locIfDelay
                           INTEGER,
                       locIfLoad
                           INTEGER,
                       locIfCollisions
                           INTEGER,
                       locIfInputQueueDrops
                           INTEGER,
                       locIfOutputQueueDrops
                           INTEGER,
                       locIfDescr
                           DisplayString,
                       locIfSlowInPkts
                           Counter,
                       locIfSlowOutPkts
                           Counter,
                       locIfSlowInOctets
                           Counter,
                       locIfSlowOutOctets
                           Counter,
                       locIfFastInPkts
                           Counter,
                       locIfFastOutPkts
                           Counter,
                       locIfFastInOctets
                           Counter,
                       locIfFastOutOctets
                           Counter,
                       locIfotherInPkts
                           Counter,
                       locIfotherOutPkts
                           Counter,
                       locIfotherInOctets
                           Counter,
                       locIfotherOutOctets
                           Counter,





          -- cisco MIB                                         [Page 27]
--





          -- Request for Comments: Draft             cisco Systems, Inc.


                       locIfipInPkts
                           Counter,
                       locIfipOutPkts
                           Counter,
                       locIfipInOctets
                           Counter,
                       locIfipOutOctets
                           Counter,
                       locIfdecnetInPkts
                           Counter,
                       locIfdecnetOutPkts
                           Counter,
                       locIfdecnetInOctets
                           Counter,
                       locIfdecnetOutOctets
                           Counter,
                       locIfxnsInPkts
                           Counter,
                       locIfxnsOutPkts
                           Counter,
                       locIfxnsInOctets
                           Counter,
                       locIfxnsOutOctets
                           Counter,
                       locIfclnsInPkts
                           Counter,
                       locIfclnsOutPkts
                           Counter,
                       locIfclnsInOctets
                           Counter,
                       locIfclnsOutOctets
                           Counter,
                       locIfappletalkInPkts
                           Counter,
                       locIfappletalkOutPkts
                           Counter,
                       locIfappletalkInOctets
                           Counter,
                       locIfappletalkOutOctets
                           Counter,
                       locIfnovellInPkts
                           Counter,
                       locIfnovellOutPkts
                           Counter,
                       locIfnovellInOctets





          -- cisco MIB                                         [Page 28]
--





          -- Request for Comments: Draft             cisco Systems, Inc.


                           Counter,
                       locIfnovellOutOctets
                           Counter,
                       locIfapolloInPkts
                           Counter,
                       locIfapolloOutPkts
                           Counter,
                       locIfapolloInOctets
                           Counter,
                       locIfapolloOutOctets
                           Counter,
                       locIfvinesInPkts
                           Counter,
                       locIfvinesOutPkts
                           Counter,
                       locIfvinesInOctets
                           Counter,
                       locIfvinesOutOctets
                           Counter,
                       locIfbridgedInPkts
                           Counter,
                       locIfbridgedOutPkts
                           Counter,
                       locIfbridgedInOctets
                           Counter,
                       locIfbridgedOutOctets
                           Counter,
                       locIfsrbInPkts
                           Counter,
                       locIfsrbOutPkts
                           Counter,
                       locIfsrbInOctets
                           Counter,
                       locIfsrbOutOctets
                           Counter,
                       locIfchaosInPkts
                           Counter,
                       locIfchaosOutPkts
                           Counter,
                       locIfchaosInOctets
                           Counter,
                       locIfchaosOutOctets
                           Counter,
                       locIfpupInPkts
                           Counter,





          -- cisco MIB                                         [Page 29]
--





          -- Request for Comments: Draft             cisco Systems, Inc.


                       locIfpupOutPkts
                           Counter,
                       locIfpupInOctets
                           Counter,
                       locIfpupOutOctets
                           Counter,
                       locIfmopInPkts
                           Counter,
                       locIfmopOutPkts
                           Counter,
                       locIfmopInOctets
                           Counter,
                       locIfmopOutOctets
                           Counter,
                       locIflanmanInPkts
                           Counter,
                       locIflanmanOutPkts
                           Counter,
                       locIflanmanInOctets
                           Counter,
                       locIflanmanOutOctets
                           Counter,
                       locIfstunInPkts
                           Counter,
                       locIfstunOutPkts
                           Counter,
                       locIfstunInOctets
                           Counter,
                       locIfstunOutOctets
                           Counter,
                       locIfspanInPkts
                           Counter,
                       locIfspanOutPkts
                           Counter,
                       locIfspanInOctets
                           Counter,
                       locIfspanOutOctets
                           Counter,
                       locIfarpInPkts
                           Counter,
                       locIfarpOutPkts
                           Counter,
                       locIfarpInOctets
                           Counter,
                       locIfarpOutOctets





          -- cisco MIB                                         [Page 30]
--





          -- Request for Comments: Draft             cisco Systems, Inc.


                           Counter,
                       locIfprobeInPkts
                           Counter,
                       locIfprobeOutPkts
                           Counter,
                       locIfprobeInOctets
                           Counter,
                       locIfprobeOutOctets
                           Counter,
                       locIfDribbleInputs
                           Counter
                   }


          -- The following section describes the components of the
          -- table.

               locIfHardType OBJECT-TYPE
                   SYNTAX  DisplayString
                   ACCESS  read-only
                   STATUS  mandatory
                   DESCRIPTION
                           "Returns the type of interface."
                   ::= { lifEntry 1 }

               locIfLineProt OBJECT-TYPE
                   SYNTAX  INTEGER
                   ACCESS  read-only
                   STATUS  mandatory
                   DESCRIPTION
                           "Boolean whether interface line protocol is
                           up or not."
                   ::= { lifEntry 2 }

               locIfLastIn OBJECT-TYPE
                   SYNTAX  INTEGER
                   ACCESS  read-only
                   STATUS  mandatory
                   DESCRIPTION
                           "Elapsed time in milliseconds since last line
                           protocol input packet was received."
                   ::= { lifEntry 3 }

               locIfLastOut OBJECT-TYPE
                   SYNTAX  INTEGER





          -- cisco MIB                                         [Page 31]
--





          -- Request for Comments: Draft             cisco Systems, Inc.


                   ACCESS  read-only
                   STATUS  mandatory
                   DESCRIPTION
                           "Elapsed time in milliseconds since last line
                           protocol output packet was transmitted."
                   ::= { lifEntry 4 }

               locIfLastOutHang OBJECT-TYPE
                   SYNTAX  INTEGER
                   ACCESS  read-only
                   STATUS  mandatory
                   DESCRIPTION
                           "Elapsed time in milliseconds since last line
                           protocol output packet could not be
                           successfully transmitted."
                   ::= { lifEntry 5 }

               locIfInBitsSec OBJECT-TYPE
                   SYNTAX  INTEGER
                   ACCESS  read-only
                   STATUS  mandatory
                   DESCRIPTION
                           "Five minute exponentially-decayed moving
                           average of input bits per second."
                   ::= { lifEntry 6 }

               locIfInPktsSec OBJECT-TYPE
                   SYNTAX  INTEGER
                   ACCESS  read-only
                   STATUS  mandatory
                   DESCRIPTION
                           "Five minute exponentially-decayed moving
                           average of input packets per second."
                   ::= { lifEntry 7 }

               locIfOutBitsSec OBJECT-TYPE
                   SYNTAX  INTEGER
                   ACCESS  read-only
                   STATUS  mandatory
                   DESCRIPTION
                           "Five minute exponentially-decayed moving
                           average of output bits per second."
                   ::= { lifEntry 8 }

               locIfOutPktsSec OBJECT-TYPE





          -- cisco MIB                                         [Page 32]
--





          -- Request for Comments: Draft             cisco Systems, Inc.


                   SYNTAX  INTEGER
                   ACCESS  read-only
                   STATUS  mandatory
                   DESCRIPTION
                           "Five minute exponentially-decayed moving
                           average of output packets per second."
                   ::= { lifEntry 9 }

               locIfInRunts OBJECT-TYPE
                   SYNTAX  INTEGER
                   ACCESS  read-only
                   STATUS  mandatory
                   DESCRIPTION
                           "Number of packets input which were smaller
                           then the allowable physical media permitted."
                   ::= { lifEntry 10 }

               locIfInGiants OBJECT-TYPE
                   SYNTAX  INTEGER
                   ACCESS  read-only
                   STATUS  mandatory
                   DESCRIPTION
                           "Number of input packets which were larger
                           then the physical media permitted."
                   ::= { lifEntry 11 }

               locIfInCRC OBJECT-TYPE
                   SYNTAX  INTEGER
                   ACCESS  read-only
                   STATUS  mandatory
                   DESCRIPTION
                           "Number of input packets which had cyclic
                           redundancy checksum errors."
                   ::= { lifEntry 12 }

               locIfInFrame OBJECT-TYPE
                   SYNTAX  INTEGER
                   ACCESS  read-only
                   STATUS  mandatory
                   DESCRIPTION
                           "Number of input packet which were
                           misaligned."
                   ::= { lifEntry 13 }

               locIfInOverrun OBJECT-TYPE





          -- cisco MIB                                         [Page 33]
--





          -- Request for Comments: Draft             cisco Systems, Inc.


                   SYNTAX  INTEGER
                   ACCESS  read-only
                   STATUS  mandatory
                   DESCRIPTION
                           "Count of input which arrived too quickly for
                           the to hardware receive."
                   ::= { lifEntry 14 }

               locIfInIgnored OBJECT-TYPE
                   SYNTAX  INTEGER
                   ACCESS  read-only
                   STATUS  mandatory
                   DESCRIPTION
                           "Number of input packets which were simply
                           ignored by this interface."
                   ::= { lifEntry 15 }

               locIfInAbort OBJECT-TYPE
                   SYNTAX  INTEGER
                   ACCESS  read-only
                   STATUS  mandatory
                   DESCRIPTION
                           "Number of input packets which were aborted."
                   ::= { lifEntry 16 }

               locIfResets OBJECT-TYPE
                   SYNTAX  INTEGER
                   ACCESS  read-only
                   STATUS  mandatory
                   DESCRIPTION
                           "Number of times the interface internally
                           reset."
                   ::= { lifEntry 17 }

               locIfRestarts OBJECT-TYPE
                   SYNTAX  INTEGER
                   ACCESS  read-only
                   STATUS  mandatory
                   DESCRIPTION
                           "Number of times interface needed to be
                           completely restarted."
                   ::= { lifEntry 18 }

               locIfKeep OBJECT-TYPE
                   SYNTAX  INTEGER





          -- cisco MIB                                         [Page 34]
--





          -- Request for Comments: Draft             cisco Systems, Inc.


                   ACCESS  read-only
                   STATUS  mandatory
                   DESCRIPTION
                           "Boolean whether keepalives are enabled on
                           this interface."
                   ::= { lifEntry 19 }

               locIfReason OBJECT-TYPE
                   SYNTAX  DisplayString
                   ACCESS  read-only
                   STATUS  mandatory
                   DESCRIPTION
                           "Reason for interface last status change."
                   ::= { lifEntry 20 }

               locIfCarTrans OBJECT-TYPE
                   SYNTAX  INTEGER
                   ACCESS  read-only
                   STATUS  mandatory
                   DESCRIPTION
                           "Number of times interface saw the carrier
                           signal transition."
                   ::= { lifEntry 21 }

               locIfReliab OBJECT-TYPE
                   SYNTAX  INTEGER
                   ACCESS  read-only
                   STATUS  mandatory
                   DESCRIPTION
                           "The reliability of the interface. Used by
                           IGRP."
                   ::= { lifEntry 22 }

               locIfDelay OBJECT-TYPE
                   SYNTAX  INTEGER
                   ACCESS  read-only
                   STATUS  mandatory
                   DESCRIPTION
                           "The amount of delay in microseconds of the
                           interface. Used by IGRP."
                   ::= { lifEntry 23 }

               locIfLoad OBJECT-TYPE
                   SYNTAX  INTEGER
                   ACCESS  read-only





          -- cisco MIB                                         [Page 35]
--





          -- Request for Comments: Draft             cisco Systems, Inc.


                   STATUS  mandatory
                   DESCRIPTION
                           "The loading factor of the interface. Used by
                           IGRP."
                   ::= { lifEntry 24 }

               locIfCollisions OBJECT-TYPE
                   SYNTAX  INTEGER
                   ACCESS  read-only
                   STATUS  mandatory
                   DESCRIPTION
                           "The number of output collisions detected on
                           this interface."
                   ::= { lifEntry 25 }

               locIfInputQueueDrops OBJECT-TYPE
                   SYNTAX  INTEGER
                   ACCESS  read-only
                   STATUS  mandatory
                   DESCRIPTION
                           "The number of packets dropped because the
                           input queue was full."
                   ::= { lifEntry 26 }

               locIfOutputQueueDrops OBJECT-TYPE
                   SYNTAX  INTEGER
                   ACCESS  read-only
                   STATUS  mandatory
                   DESCRIPTION
                           "The number of packets dropped because the
                           output queue was full."
                   ::= { lifEntry 27 }

               locIfDescr OBJECT-TYPE
                   SYNTAX  DisplayString
                   ACCESS  read-write
                   STATUS  mandatory
                   DESCRIPTION
                           "User configurable interface description."
                   ::= { lifEntry 28 }

               locIfSlowInPkts OBJECT-TYPE
                   SYNTAX  Counter
                   ACCESS  read-only
                   STATUS  mandatory





          -- cisco MIB                                         [Page 36]
--





          -- Request for Comments: Draft             cisco Systems, Inc.


                   DESCRIPTION
                           "Packet count for Inbound traffic routed with
                           slow switching"
                   ::= { lifEntry 30 }

               locIfSlowOutPkts OBJECT-TYPE
                   SYNTAX  Counter
                   ACCESS  read-only
                   STATUS  mandatory
                   DESCRIPTION
                           "Packet count for Outbound traffic routed
                           with slow switching"
                   ::= { lifEntry 31 }

               locIfSlowInOctets OBJECT-TYPE
                   SYNTAX  Counter
                   ACCESS  read-only
                   STATUS  mandatory
                   DESCRIPTION
                           "Octet count for Inbound traffic routed with
                           slow switching"
                   ::= { lifEntry 32 }

               locIfSlowOutOctets OBJECT-TYPE
                   SYNTAX  Counter
                   ACCESS  read-only
                   STATUS  mandatory
                   DESCRIPTION
                           "Octet count for Outbound traffic routed with
                           slow switching"
                   ::= { lifEntry 33 }

               locIfFastInPkts OBJECT-TYPE
                   SYNTAX  Counter
                   ACCESS  read-only
                   STATUS  mandatory
                   DESCRIPTION
                           "Packet count for Inbound traffic routed with
                           fast switching"
                   ::= { lifEntry 34 }

               locIfFastOutPkts OBJECT-TYPE
                   SYNTAX  Counter
                   ACCESS  read-only
                   STATUS  mandatory





          -- cisco MIB                                         [Page 37]
--





          -- Request for Comments: Draft             cisco Systems, Inc.


                   DESCRIPTION
                           "Packet count for Outbound traffic routed
                           with fast switching"
                   ::= { lifEntry 35 }

               locIfFastInOctets OBJECT-TYPE
                   SYNTAX  Counter
                   ACCESS  read-only
                   STATUS  mandatory
                   DESCRIPTION
                           "Octet count for Inbound traffic routed with
                           fast switching"
                   ::= { lifEntry 36 }

               locIfFastOutOctets OBJECT-TYPE
                   SYNTAX  Counter
                   ACCESS  read-only
                   STATUS  mandatory
                   DESCRIPTION
                           "Octet count for Outbound traffic routed with
                           fast switching"
                   ::= { lifEntry 37 }

               locIfotherInPkts OBJECT-TYPE
                   SYNTAX  Counter
                   ACCESS  read-only
                   STATUS  mandatory
                   DESCRIPTION
                           "Other protocol input packet count"
                   ::= { lifEntry 38 }

               locIfotherOutPkts OBJECT-TYPE
                   SYNTAX  Counter
                   ACCESS  read-only
                   STATUS  mandatory
                   DESCRIPTION
                           "Other protocol output packet count"
                   ::= { lifEntry 39 }

               locIfotherInOctets OBJECT-TYPE
                   SYNTAX  Counter
                   ACCESS  read-only
                   STATUS  mandatory
                   DESCRIPTION
                           "Other protocol input octet count"





          -- cisco MIB                                         [Page 38]
--





          -- Request for Comments: Draft             cisco Systems, Inc.


                   ::= { lifEntry 40 }

               locIfotherOutOctets OBJECT-TYPE
                   SYNTAX  Counter
                   ACCESS  read-only
                   STATUS  mandatory
                   DESCRIPTION
                           "Other protocol output octet count"
                   ::= { lifEntry 41 }

               locIfipInPkts OBJECT-TYPE
                   SYNTAX  Counter
                   ACCESS  read-only
                   STATUS  mandatory
                   DESCRIPTION
                           "ip protocol input packet count"
                   ::= { lifEntry 42 }

               locIfipOutPkts OBJECT-TYPE
                   SYNTAX  Counter
                   ACCESS  read-only
                   STATUS  mandatory
                   DESCRIPTION
                           "ip protocol output packet count"
                   ::= { lifEntry 43 }

               locIfipInOctets OBJECT-TYPE
                   SYNTAX  Counter
                   ACCESS  read-only
                   STATUS  mandatory
                   DESCRIPTION
                           "ip protocol input octet count"
                   ::= { lifEntry 44 }

               locIfipOutOctets OBJECT-TYPE
                   SYNTAX  Counter
                   ACCESS  read-only
                   STATUS  mandatory
                   DESCRIPTION
                           "ip protocol output octet count"
                   ::= { lifEntry 45 }

               locIfdecnetInPkts OBJECT-TYPE
                   SYNTAX  Counter
                   ACCESS  read-only





          -- cisco MIB                                         [Page 39]
--





          -- Request for Comments: Draft             cisco Systems, Inc.


                   STATUS  mandatory
                   DESCRIPTION
                           "Decnet protocol input packet count"
                   ::= { lifEntry 46 }

               locIfdecnetOutPkts OBJECT-TYPE
                   SYNTAX  Counter
                   ACCESS  read-only
                   STATUS  mandatory
                   DESCRIPTION
                           "Decnet protocol output packet count"
                   ::= { lifEntry 47 }

               locIfdecnetInOctets OBJECT-TYPE
                   SYNTAX  Counter
                   ACCESS  read-only
                   STATUS  mandatory
                   DESCRIPTION
                           "Decnet protocol input byte count"
                   ::= { lifEntry 48 }

               locIfdecnetOutOctets OBJECT-TYPE
                   SYNTAX  Counter
                   ACCESS  read-only
                   STATUS  mandatory
                   DESCRIPTION
                           "Decnet protocol output byte count"
                   ::= { lifEntry 49 }

               locIfxnsInPkts OBJECT-TYPE
                   SYNTAX  Counter
                   ACCESS  read-only
                   STATUS  mandatory
                   DESCRIPTION
                           "XNS protocol input packet count"
                   ::= { lifEntry 50 }

               locIfxnsOutPkts OBJECT-TYPE
                   SYNTAX  Counter
                   ACCESS  read-only
                   STATUS  mandatory
                   DESCRIPTION
                           "XNS protocol output packet count"
                   ::= { lifEntry 51 }






          -- cisco MIB                                         [Page 40]
--





          -- Request for Comments: Draft             cisco Systems, Inc.


               locIfxnsInOctets OBJECT-TYPE
                   SYNTAX  Counter
                   ACCESS  read-only
                   STATUS  mandatory
                   DESCRIPTION
                           "XNS protocol input byte count"
                   ::= { lifEntry 52 }

               locIfxnsOutOctets OBJECT-TYPE
                   SYNTAX  Counter
                   ACCESS  read-only
                   STATUS  mandatory
                   DESCRIPTION
                           "XNS protocol output byte count"
                   ::= { lifEntry 53 }

               locIfclnsInPkts OBJECT-TYPE
                   SYNTAX  Counter
                   ACCESS  read-only
                   STATUS  mandatory
                   DESCRIPTION
                           "CLNS protocol input packet count"
                   ::= { lifEntry 54 }

               locIfclnsOutPkts OBJECT-TYPE
                   SYNTAX  Counter
                   ACCESS  read-only
                   STATUS  mandatory
                   DESCRIPTION
                           "CLNS protocol output packet count"
                   ::= { lifEntry 55 }

               locIfclnsInOctets OBJECT-TYPE
                   SYNTAX  Counter
                   ACCESS  read-only
                   STATUS  mandatory
                   DESCRIPTION
                           "CLNS protocol input byte count"
                   ::= { lifEntry 56 }

               locIfclnsOutOctets OBJECT-TYPE
                   SYNTAX  Counter
                   ACCESS  read-only
                   STATUS  mandatory
                   DESCRIPTION





          -- cisco MIB                                         [Page 41]
--





          -- Request for Comments: Draft             cisco Systems, Inc.


                           "CLNS protocol output byte count"
                   ::= { lifEntry 57 }

               locIfappletalkInPkts OBJECT-TYPE
                   SYNTAX  Counter
                   ACCESS  read-only
                   STATUS  mandatory
                   DESCRIPTION
                           "Appletalk protocol input packet count"
                   ::= { lifEntry 58 }

               locIfappletalkOutPkts OBJECT-TYPE
                   SYNTAX  Counter
                   ACCESS  read-only
                   STATUS  mandatory
                   DESCRIPTION
                           "Appletalk protocol output packet count"
                   ::= { lifEntry 59 }

               locIfappletalkInOctets OBJECT-TYPE
                   SYNTAX  Counter
                   ACCESS  read-only
                   STATUS  mandatory
                   DESCRIPTION
                           "Appletalk protocol input octet count"
                   ::= { lifEntry 60 }

               locIfappletalkOutOctets OBJECT-TYPE
                   SYNTAX  Counter
                   ACCESS  read-only
                   STATUS  mandatory
                   DESCRIPTION
                           "Appletalk protocol output octet count"
                   ::= { lifEntry 61 }

               locIfnovellInPkts OBJECT-TYPE
                   SYNTAX  Counter
                   ACCESS  read-only
                   STATUS  mandatory
                   DESCRIPTION
                           "Novell protocol input packet count"
                   ::= { lifEntry 62 }

               locIfnovellOutPkts OBJECT-TYPE
                   SYNTAX  Counter





          -- cisco MIB                                         [Page 42]
--





          -- Request for Comments: Draft             cisco Systems, Inc.


                   ACCESS  read-only
                   STATUS  mandatory
                   DESCRIPTION
                           "Novell protocol output packet count"
                   ::= { lifEntry 63 }

               locIfnovellInOctets OBJECT-TYPE
                   SYNTAX  Counter
                   ACCESS  read-only
                   STATUS  mandatory
                   DESCRIPTION
                           "Novell protocol input octet count"
                   ::= { lifEntry 64 }

               locIfnovellOutOctets OBJECT-TYPE
                   SYNTAX  Counter
                   ACCESS  read-only
                   STATUS  mandatory
                   DESCRIPTION
                           "Novell protocol output octet count"
                   ::= { lifEntry 65 }

               locIfapolloInPkts OBJECT-TYPE
                   SYNTAX  Counter
                   ACCESS  read-only
                   STATUS  mandatory
                   DESCRIPTION
                           "Apollo protocol input packet count"
                   ::= { lifEntry 66 }

               locIfapolloOutPkts OBJECT-TYPE
                   SYNTAX  Counter
                   ACCESS  read-only
                   STATUS  mandatory
                   DESCRIPTION
                           "Apollo protocol output packet count"
                   ::= { lifEntry 67 }

               locIfapolloInOctets OBJECT-TYPE
                   SYNTAX  Counter
                   ACCESS  read-only
                   STATUS  mandatory
                   DESCRIPTION
                           "Apollo protocol input octet count"
                   ::= { lifEntry 68 }





          -- cisco MIB                                         [Page 43]
--





          -- Request for Comments: Draft             cisco Systems, Inc.


               locIfapolloOutOctets OBJECT-TYPE
                   SYNTAX  Counter
                   ACCESS  read-only
                   STATUS  mandatory
                   DESCRIPTION
                           "Apollo protocol output octet count"
                   ::= { lifEntry 69 }

               locIfvinesInPkts OBJECT-TYPE
                   SYNTAX  Counter
                   ACCESS  read-only
                   STATUS  mandatory
                   DESCRIPTION
                           "Vines protocol input packet count"
                   ::= { lifEntry 70 }

               locIfvinesOutPkts OBJECT-TYPE
                   SYNTAX  Counter
                   ACCESS  read-only
                   STATUS  mandatory
                   DESCRIPTION
                           "Vines protocol output packet count"
                   ::= { lifEntry 71 }

               locIfvinesInOctets OBJECT-TYPE
                   SYNTAX  Counter
                   ACCESS  read-only
                   STATUS  mandatory
                   DESCRIPTION
                           "Vines protocol input octet count"
                   ::= { lifEntry 72 }

               locIfvinesOutOctets OBJECT-TYPE
                   SYNTAX  Counter
                   ACCESS  read-only
                   STATUS  mandatory
                   DESCRIPTION
                           "Vines protocol output octet count"
                   ::= { lifEntry 73 }

               locIfbridgedInPkts OBJECT-TYPE
                   SYNTAX  Counter
                   ACCESS  read-only
                   STATUS  mandatory
                   DESCRIPTION





          -- cisco MIB                                         [Page 44]
--





          -- Request for Comments: Draft             cisco Systems, Inc.


                           "Bridged protocol input packet count"
                   ::= { lifEntry 74 }

               locIfbridgedOutPkts OBJECT-TYPE
                   SYNTAX  Counter
                   ACCESS  read-only
                   STATUS  mandatory
                   DESCRIPTION
                           "Bridged protocol output packet count"
                   ::= { lifEntry 75 }

               locIfbridgedInOctets OBJECT-TYPE
                   SYNTAX  Counter
                   ACCESS  read-only
                   STATUS  mandatory
                   DESCRIPTION
                           "Bridged protocol input octet count"
                   ::= { lifEntry 76 }

               locIfbridgedOutOctets OBJECT-TYPE
                   SYNTAX  Counter
                   ACCESS  read-only
                   STATUS  mandatory
                   DESCRIPTION
                           "Bridged protocol output octet count"
                   ::= { lifEntry 77 }

               locIfsrbInPkts OBJECT-TYPE
                   SYNTAX  Counter
                   ACCESS  read-only
                   STATUS  mandatory
                   DESCRIPTION
                           "SRB protocol input packet count"
                   ::= { lifEntry 78 }

               locIfsrbOutPkts OBJECT-TYPE
                   SYNTAX  Counter
                   ACCESS  read-only
                   STATUS  mandatory
                   DESCRIPTION
                           "SRB protocol output packet count"
                   ::= { lifEntry 79 }

               locIfsrbInOctets OBJECT-TYPE
                   SYNTAX  Counter





          -- cisco MIB                                         [Page 45]
--





          -- Request for Comments: Draft             cisco Systems, Inc.


                   ACCESS  read-only
                   STATUS  mandatory
                   DESCRIPTION
                           "SRB protocol input octet count"
                   ::= { lifEntry 80 }

               locIfsrbOutOctets OBJECT-TYPE
                   SYNTAX  Counter
                   ACCESS  read-only
                   STATUS  mandatory
                   DESCRIPTION
                           "SRB protocol output octet count"
                   ::= { lifEntry 81 }

               locIfchaosInPkts OBJECT-TYPE
                   SYNTAX  Counter
                   ACCESS  read-only
                   STATUS  mandatory
                   DESCRIPTION
                           "Choas protocol input packet count"
                   ::= { lifEntry 82 }

               locIfchaosOutPkts OBJECT-TYPE
                   SYNTAX  Counter
                   ACCESS  read-only
                   STATUS  mandatory
                   DESCRIPTION
                           "Choas protocol output packet count"
                   ::= { lifEntry 83 }

               locIfchaosInOctets OBJECT-TYPE
                   SYNTAX  Counter
                   ACCESS  read-only
                   STATUS  mandatory
                   DESCRIPTION
                           "Choas protocol input octet count"
                   ::= { lifEntry 84 }

               locIfchaosOutOctets OBJECT-TYPE
                   SYNTAX  Counter
                   ACCESS  read-only
                   STATUS  mandatory
                   DESCRIPTION
                           "Choas protocol output octet count"
                   ::= { lifEntry 85 }





          -- cisco MIB                                         [Page 46]
--





          -- Request for Comments: Draft             cisco Systems, Inc.


               locIfpupInPkts OBJECT-TYPE
                   SYNTAX  Counter
                   ACCESS  read-only
                   STATUS  mandatory
                   DESCRIPTION
                           "PUP protocol input packet count"
                   ::= { lifEntry 86 }

               locIfpupOutPkts OBJECT-TYPE
                   SYNTAX  Counter
                   ACCESS  read-only
                   STATUS  mandatory
                   DESCRIPTION
                           "PUP protocol output packet count"
                   ::= { lifEntry 87 }

               locIfpupInOctets OBJECT-TYPE
                   SYNTAX  Counter
                   ACCESS  read-only
                   STATUS  mandatory
                   DESCRIPTION
                           "PUP protocol input octet count"
                   ::= { lifEntry 88 }

               locIfpupOutOctets OBJECT-TYPE
                   SYNTAX  Counter
                   ACCESS  read-only
                   STATUS  mandatory
                   DESCRIPTION
                           "PUP protocol output octet count"
                   ::= { lifEntry 89 }

               locIfmopInPkts OBJECT-TYPE
                   SYNTAX  Counter
                   ACCESS  read-only
                   STATUS  mandatory
                   DESCRIPTION
                           "MOP protocol input packet count"
                   ::= { lifEntry 90 }

               locIfmopOutPkts OBJECT-TYPE
                   SYNTAX  Counter
                   ACCESS  read-only
                   STATUS  mandatory
                   DESCRIPTION





          -- cisco MIB                                         [Page 47]
--





          -- Request for Comments: Draft             cisco Systems, Inc.


                           "MOP protocol output packet count"
                   ::= { lifEntry 91 }

               locIfmopInOctets OBJECT-TYPE
                   SYNTAX  Counter
                   ACCESS  read-only
                   STATUS  mandatory
                   DESCRIPTION
                           "MOP protocol input octet count"
                   ::= { lifEntry 92 }

               locIfmopOutOctets OBJECT-TYPE
                   SYNTAX  Counter
                   ACCESS  read-only
                   STATUS  mandatory
                   DESCRIPTION
                           "MOP protocol output octet count"
                   ::= { lifEntry 93 }

               locIflanmanInPkts OBJECT-TYPE
                   SYNTAX  Counter
                   ACCESS  read-only
                   STATUS  mandatory
                   DESCRIPTION
                           "LanMan protocol input packet count"
                   ::= { lifEntry 94 }

               locIflanmanOutPkts OBJECT-TYPE
                   SYNTAX  Counter
                   ACCESS  read-only
                   STATUS  mandatory
                   DESCRIPTION
                           "LanMan protocol output packet count"
                   ::= { lifEntry 95 }

               locIflanmanInOctets OBJECT-TYPE
                   SYNTAX  Counter
                   ACCESS  read-only
                   STATUS  mandatory
                   DESCRIPTION
                           "LanMan protocol input octet count"
                   ::= { lifEntry 96 }

               locIflanmanOutOctets OBJECT-TYPE
                   SYNTAX  Counter





          -- cisco MIB                                         [Page 48]
--





          -- Request for Comments: Draft             cisco Systems, Inc.


                   ACCESS  read-only
                   STATUS  mandatory
                   DESCRIPTION
                           "LanMan protocol output octet count"
                   ::= { lifEntry 97 }

               locIfstunInPkts OBJECT-TYPE
                   SYNTAX  Counter
                   ACCESS  read-only
                   STATUS  mandatory
                   DESCRIPTION
                           "STUN protocol input packet count"
                   ::= { lifEntry 98 }

               locIfstunOutPkts OBJECT-TYPE
                   SYNTAX  Counter
                   ACCESS  read-only
                   STATUS  mandatory
                   DESCRIPTION
                           "STUN protocol output packet count"
                   ::= { lifEntry 99 }

               locIfstunInOctets OBJECT-TYPE
                   SYNTAX  Counter
                   ACCESS  read-only
                   STATUS  mandatory
                   DESCRIPTION
                           "STUN protocol input octet count"
                   ::= { lifEntry 100 }

               locIfstunOutOctets OBJECT-TYPE
                   SYNTAX  Counter
                   ACCESS  read-only
                   STATUS  mandatory
                   DESCRIPTION
                           "STUN protocol output octet count"
                   ::= { lifEntry 101 }

               locIfspanInPkts OBJECT-TYPE
                   SYNTAX  Counter
                   ACCESS  read-only
                   STATUS  mandatory
                   DESCRIPTION
                           "Spanning tree input protocol packet count"
                   ::= { lifEntry 102 }





          -- cisco MIB                                         [Page 49]
--





          -- Request for Comments: Draft             cisco Systems, Inc.


               locIfspanOutPkts OBJECT-TYPE
                   SYNTAX  Counter
                   ACCESS  read-only
                   STATUS  mandatory
                   DESCRIPTION
                           "Spanning tree output protocol packet count"
                   ::= { lifEntry 103 }

               locIfspanInOctets OBJECT-TYPE
                   SYNTAX  Counter
                   ACCESS  read-only
                   STATUS  mandatory
                   DESCRIPTION
                           "Spanning tree input octet packet count"
                   ::= { lifEntry 104 }

               locIfspanOutOctets OBJECT-TYPE
                   SYNTAX  Counter
                   ACCESS  read-only
                   STATUS  mandatory
                   DESCRIPTION
                           "Spanning tree output octet packet count"
                   ::= { lifEntry 105 }

               locIfarpInPkts OBJECT-TYPE
                   SYNTAX  Counter
                   ACCESS  read-only
                   STATUS  mandatory
                   DESCRIPTION
                           "Arp protocol input packet count"
                   ::= { lifEntry 106 }

               locIfarpOutPkts OBJECT-TYPE
                   SYNTAX  Counter
                   ACCESS  read-only
                   STATUS  mandatory
                   DESCRIPTION
                           "Arp protocol output packet count"
                   ::= { lifEntry 107 }

               locIfarpInOctets OBJECT-TYPE
                   SYNTAX  Counter
                   ACCESS  read-only
                   STATUS  mandatory
                   DESCRIPTION





          -- cisco MIB                                         [Page 50]
--





          -- Request for Comments: Draft             cisco Systems, Inc.


                           "Arp protocol input octet count"
                   ::= { lifEntry 108 }

               locIfarpOutOctets OBJECT-TYPE
                   SYNTAX  Counter
                   ACCESS  read-only
                   STATUS  mandatory
                   DESCRIPTION
                           "Arp protocol output octet count"
                   ::= { lifEntry 109 }

               locIfprobeInPkts OBJECT-TYPE
                   SYNTAX  Counter
                   ACCESS  read-only
                   STATUS  mandatory
                   DESCRIPTION
                           "Probe protocol input packet count"
                   ::= { lifEntry 110 }

               locIfprobeOutPkts OBJECT-TYPE
                   SYNTAX  Counter
                   ACCESS  read-only
                   STATUS  mandatory
                   DESCRIPTION
                           "Probe protocol output packet count"
                   ::= { lifEntry 111 }

               locIfprobeInOctets OBJECT-TYPE
                   SYNTAX  Counter
                   ACCESS  read-only
                   STATUS  mandatory
                   DESCRIPTION
                           "Probe protocol input octet count"
                   ::= { lifEntry 112 }

               locIfprobeOutOctets OBJECT-TYPE
                   SYNTAX  Counter
                   ACCESS  read-only
                   STATUS  mandatory
                   DESCRIPTION
                           "Probe protocol output octet count"
                   ::= { lifEntry 113 }

               locIfDribbleInputs OBJECT-TYPE
                   SYNTAX  Counter





          -- cisco MIB                                         [Page 51]
--





          -- Request for Comments: Draft             cisco Systems, Inc.


                   ACCESS  read-only
                   STATUS  mandatory
                   DESCRIPTION
                           "The number of good packets received with the
                           dribble condition present"
                   ::= { lifEntry 114 }

               -- End of table



               -- Local FSIP card Table

          -- This group provides additional objects to the table
          -- defined by RFC1156.

               lFSIPTable OBJECT-TYPE
                   SYNTAX  SEQUENCE OF LFSIPEntry
                   ACCESS  not-accessible
                   STATUS  mandatory
                   DESCRIPTION
                            "A list of FSIP card entries."
                   ::= { linterfaces 2 }

               lFSIPEntry OBJECT-TYPE
                   SYNTAX LFSIPEntry
                   ACCESS  not-accessible
                   STATUS  mandatory
                   DESCRIPTION
                            "A collection of objects specific to the
                            FSIP card."
                   INDEX { locIfFSIPIndex }
               ::= { lFSIPTable 1 }

               LFSIPEntry ::=
                   SEQUENCE {
                       locIfFSIPIndex
                           INTEGER,
                       locIfFSIPtype
                           INTEGER,
                       locIfFSIPrts
                           INTEGER,
                       locIfFSIPcts
                           INTEGER,
                       locIfFSIPdtr





          -- cisco MIB                                         [Page 52]
--





          -- Request for Comments: Draft             cisco Systems, Inc.


                           INTEGER,
                       locIfFSIPdcd
                           INTEGER,
                       locIfFSIPdsr
                           INTEGER
                   }


          -- The following section describes the components of the
          -- table.

               locIfFSIPIndex OBJECT-TYPE
                   SYNTAX  INTEGER
                   ACCESS  read-only
                   STATUS  mandatory
                   DESCRIPTION
                           "Interface index of this card corresponding
                           to its ifIndex"
                   ::= { lFSIPEntry 1 }

               locIfFSIPtype OBJECT-TYPE
                   SYNTAX  INTEGER {
                        notAvailable(1),
                        dte(2),
                        dce(3)
                   }
                   ACCESS  read-only
                   STATUS  mandatory
                   DESCRIPTION
                           "Is this FSIP line DCE or DTE"
                   ::= { lFSIPEntry 2 }

               locIfFSIPrts OBJECT-TYPE
                   SYNTAX  INTEGER {
                        notAvailable(1),
                        up(2),
                        down(3)
                   }
                   ACCESS  read-only
                   STATUS  mandatory
                   DESCRIPTION
                           "Is the RTS signal up or down"
                   ::= { lFSIPEntry 3 }

               locIfFSIPcts OBJECT-TYPE





          -- cisco MIB                                         [Page 53]
--





          -- Request for Comments: Draft             cisco Systems, Inc.


                   SYNTAX  INTEGER {
                        notAvailable(1),
                        up(2),
                        down(3)
                   }
                   ACCESS  read-only
                   STATUS  mandatory
                   DESCRIPTION
                           "Is the CTS signal up or down"
                   ::= { lFSIPEntry 4 }

               locIfFSIPdtr OBJECT-TYPE
                   SYNTAX  INTEGER {
                        notAvailable(1),
                        up(2),
                        down(3)
                   }
                   ACCESS  read-only
                   STATUS  mandatory
                   DESCRIPTION
                           "Is the DTR signal up or down"
                   ::= { lFSIPEntry 5 }

               locIfFSIPdcd OBJECT-TYPE
                   SYNTAX  INTEGER {
                        notAvailable(1),
                        up(2),
                        down(3)
                   }
                   ACCESS  read-only
                   STATUS  mandatory
                   DESCRIPTION
                           "Is the DCD signal up or down"
                   ::= { lFSIPEntry 6 }

               locIfFSIPdsr OBJECT-TYPE
                   SYNTAX  INTEGER {
                        notAvailable(1),
                        up(2),
                        down(3)
                   }
                   ACCESS  read-only
                   STATUS  mandatory
                   DESCRIPTION
                           "Is the DSR signal up or down"





          -- cisco MIB                                         [Page 54]
--





          -- Request for Comments: Draft             cisco Systems, Inc.


                   ::= { lFSIPEntry 7 }

               -- End of table



               -- Local IP Group

          -- This group is present in all products which are using the
          -- IP protocol.


          -- Local IP Address Table

          -- This group provides additional objects to the table
          -- defined by RFC1156.

               lipAddrTable OBJECT-TYPE
                   SYNTAX  SEQUENCE OF LIpAddrEntry
                   ACCESS  not-accessible
                   STATUS  mandatory
                   DESCRIPTION
                            "A list of IP address entries."
                   ::= { lip 1 }

               lipAddrEntry OBJECT-TYPE
                   SYNTAX LIpAddrEntry
                   ACCESS  not-accessible
                   STATUS  mandatory
                   DESCRIPTION
                            "A collection of additional objects in the
                            cisco IP implementation."
                   INDEX { ipAdEntAddr }
               ::= { lipAddrTable 1 }

               LIpAddrEntry ::=
                   SEQUENCE {
                       locIPHow
                           DisplayString,
                       locIPWho
                           IpAddress,
                       locIPHelper
                           IpAddress,
                       locIPSecurity
                           INTEGER,





          -- cisco MIB                                         [Page 55]
--





          -- Request for Comments: Draft             cisco Systems, Inc.


                       locIPRedirects
                           INTEGER,
                       locIPUnreach
                           INTEGER
                   }


          -- The following section describes the components of the
          -- table.

               locIPHow OBJECT-TYPE
                   SYNTAX  DisplayString
                   ACCESS  read-only
                   STATUS  mandatory
                   DESCRIPTION
                           "Method of how this interface obtained its IP
                           address."
                   ::= { lipAddrEntry 1 }

               locIPWho OBJECT-TYPE
                   SYNTAX  IpAddress
                   ACCESS  read-only
                   STATUS  mandatory
                   DESCRIPTION
                           "IP address of who supplied this interface
                           its IP address."
                   ::= { lipAddrEntry 2 }

               locIPHelper OBJECT-TYPE
                   SYNTAX  IpAddress
                   ACCESS  read-only
                   STATUS  mandatory
                   DESCRIPTION
                           "IP helper address for broadcast forwarding
                           support."
                   ::= { lipAddrEntry 3 }

               locIPSecurity OBJECT-TYPE
                   SYNTAX  INTEGER
                   ACCESS  read-only
                   STATUS  mandatory
                   DESCRIPTION
                           "IP security level. See RFC 1038."
                   ::= { lipAddrEntry 4 }






          -- cisco MIB                                         [Page 56]
--





          -- Request for Comments: Draft             cisco Systems, Inc.


               locIPRedirects OBJECT-TYPE
                   SYNTAX  INTEGER
                   ACCESS  read-only
                   STATUS  mandatory
                   DESCRIPTION
                           "Boolean whether ICMP redirects will be sent
                           or not."
                   ::= { lipAddrEntry 5 }

               locIPUnreach OBJECT-TYPE
                   SYNTAX  INTEGER
                   ACCESS  read-only
                   STATUS  mandatory
                   DESCRIPTION
                           "Boolean whether ICMP unreachables will be
                           sent or not."
                   ::= { lipAddrEntry 6 }

               -- End of table



               -- Local IP Routing Table

          -- This group provides additional objects to the table
          -- defined by RFC1156.

               lipRoutingTable OBJECT-TYPE
                   SYNTAX  SEQUENCE OF LIpRouteEntry
                   ACCESS  not-accessible
                   STATUS  mandatory
                   DESCRIPTION
                            "A list of IP routing entries."
                   ::= { lip 2 }

               lipRouteEntry OBJECT-TYPE
                   SYNTAX LIpRouteEntry
                   ACCESS  not-accessible
                   STATUS  mandatory
                   DESCRIPTION
                            "A collection of additional objects in the
                            cisco IP routing implementation."
                   INDEX { ipRouteDest }
               ::= { lipRoutingTable 1 }






          -- cisco MIB                                         [Page 57]
--





          -- Request for Comments: Draft             cisco Systems, Inc.


               LIpRouteEntry ::=
                   SEQUENCE {
                       locRtMask
                           IpAddress,
                       locRtCount
                           INTEGER,
                       locRtUses
                           INTEGER
                   }


          -- The following section describes the components of the
          -- table.

               locRtMask OBJECT-TYPE
                   SYNTAX  IpAddress
                   ACCESS  read-only
                   STATUS  mandatory
                   DESCRIPTION
                           "Routing table network mask."
                   ::= { lipRouteEntry 1 }

               locRtCount OBJECT-TYPE
                   SYNTAX  INTEGER
                   ACCESS  read-only
                   STATUS  mandatory
                   DESCRIPTION
                           "Number of parallel routes within routing
                           table."
                   ::= { lipRouteEntry 2 }

               locRtUses OBJECT-TYPE
                   SYNTAX  INTEGER
                   ACCESS  read-only
                   STATUS  mandatory
                   DESCRIPTION
                           "Number of times this route was used in a
                           forward operation."
                   ::= { lipRouteEntry 3 }

               -- End of table


               actThresh OBJECT-TYPE
                   SYNTAX  INTEGER





          -- cisco MIB                                         [Page 58]
--





          -- Request for Comments: Draft             cisco Systems, Inc.


                   ACCESS  read-only
                   STATUS  mandatory
                   DESCRIPTION
                           "Threshold of IP accounting records in use
                           before IP traffic will be unaccounted."
                   ::= { lip 4 }

               actLostPkts OBJECT-TYPE
                   SYNTAX  INTEGER
                   ACCESS  read-only
                   STATUS  mandatory
                   DESCRIPTION
                           "Lost IP packets due to memory limitations."
                   ::= { lip 5 }

               actLostByts OBJECT-TYPE
                   SYNTAX  INTEGER
                   ACCESS  read-only
                   STATUS  mandatory
                   DESCRIPTION
                           "Total bytes of lost IP packets."
                   ::= { lip 6 }


               -- Local IP Accounting Table

          -- This group provides access to the cisco IP accounting
          -- support.

               lipAccountingTable OBJECT-TYPE
                   SYNTAX  SEQUENCE OF LIpAccountEntry
                   ACCESS  not-accessible
                   STATUS  mandatory
                   DESCRIPTION
                            "A list of IP accounting entries."
                   ::= { lip 7 }

               lipAccountEntry OBJECT-TYPE
                   SYNTAX LIpAccountEntry
                   ACCESS  not-accessible
                   STATUS  mandatory
                   DESCRIPTION
                            "A collection of objects necessary for IP
                            accounting."
                   INDEX { actSrc, actDst }





          -- cisco MIB                                         [Page 59]
--





          -- Request for Comments: Draft             cisco Systems, Inc.


               ::= { lipAccountingTable 1 }

               LIpAccountEntry ::=
                   SEQUENCE {
                       actSrc
                           IpAddress,
                       actDst
                           IpAddress,
                       actPkts
                           INTEGER,
                       actByts
                           INTEGER
                   }


          -- The following section describes the components of the
          -- table.

               actSrc OBJECT-TYPE
                   SYNTAX  IpAddress
                   ACCESS  read-only
                   STATUS  mandatory
                   DESCRIPTION
                           "IP Source address for host traffic matrix."
                   ::= { lipAccountEntry 1 }

               actDst OBJECT-TYPE
                   SYNTAX  IpAddress
                   ACCESS  read-only
                   STATUS  mandatory
                   DESCRIPTION
                           "IP Destination address for host traffic
                           matrix."
                   ::= { lipAccountEntry 2 }

               actPkts OBJECT-TYPE
                   SYNTAX  INTEGER
                   ACCESS  read-only
                   STATUS  mandatory
                   DESCRIPTION
                           "Number of IP packets sent from source to
                           destination."
                   ::= { lipAccountEntry 3 }

               actByts OBJECT-TYPE





          -- cisco MIB                                         [Page 60]
--





          -- Request for Comments: Draft             cisco Systems, Inc.


                   SYNTAX  INTEGER
                   ACCESS  read-only
                   STATUS  mandatory
                   DESCRIPTION
                           "Total number of bytes in IP packets from
                           source to destination."
                   ::= { lipAccountEntry 4 }

               -- End of table


               actAge OBJECT-TYPE
                   SYNTAX  TimeTicks
                   ACCESS  read-only
                   STATUS  mandatory
                   DESCRIPTION
                           "The age of the data in the current data
                           matrix."
                   ::= { lip 8 }


               -- Local IP Checkpoint Accounting Table

          -- This group provides access to the cisco
          -- IP checkpoint accounting support.

               lipCkAccountingTable OBJECT-TYPE
                   SYNTAX  SEQUENCE OF LIpCkAccountEntry
                   ACCESS  not-accessible
                   STATUS  mandatory
                   DESCRIPTION
                            "A list of IP checkpoint accounting
                            entries."
                   ::= { lip 9 }

               lipCkAccountEntry OBJECT-TYPE
                   SYNTAX LIpCkAccountEntry
                   ACCESS  not-accessible
                   STATUS  mandatory
                   DESCRIPTION
                            "A collection of objects necessary for IP
                            checkpoint accounting."
                   INDEX { ckactSrc, ckactDst }
               ::= { lipCkAccountingTable 1 }






          -- cisco MIB                                         [Page 61]
--





          -- Request for Comments: Draft             cisco Systems, Inc.


               LIpCkAccountEntry ::=
                   SEQUENCE {
                       ckactSrc
                           IpAddress,
                       ckactDst
                           IpAddress,
                       ckactPkts
                           INTEGER,
                       ckactByts
                           INTEGER
                   }


          -- The following section describes the components of the
          -- table.

               ckactSrc OBJECT-TYPE
                   SYNTAX  IpAddress
                   ACCESS  read-only
                   STATUS  mandatory
                   DESCRIPTION
                           "IP Source address for host in checkpoint
                           traffic matrix."
                   ::= { lipCkAccountEntry 1 }

               ckactDst OBJECT-TYPE
                   SYNTAX  IpAddress
                   ACCESS  read-only
                   STATUS  mandatory
                   DESCRIPTION
                           "IP Destination address for host in
                           checkpoint traffic matrix."
                   ::= { lipCkAccountEntry 2 }

               ckactPkts OBJECT-TYPE
                   SYNTAX  INTEGER
                   ACCESS  read-only
                   STATUS  mandatory
                   DESCRIPTION
                           "Number of IP packets sent from source to
                           destination in checkpoint matrix."
                   ::= { lipCkAccountEntry 3 }

               ckactByts OBJECT-TYPE
                   SYNTAX  INTEGER





          -- cisco MIB                                         [Page 62]
--





          -- Request for Comments: Draft             cisco Systems, Inc.


                   ACCESS  read-only
                   STATUS  mandatory
                   DESCRIPTION
                           "Total number of bytes in IP packets from
                           source to destination in checkpoint matrix."
                   ::= { lipCkAccountEntry 4 }

               -- End of table


               ckactAge OBJECT-TYPE
                   SYNTAX  TimeTicks
                   ACCESS  read-only
                   STATUS  mandatory
                   DESCRIPTION
                           "Age of data in the checkpoint matrix."
                   ::= { lip 10 }

               actCheckPoint OBJECT-TYPE
                   SYNTAX  INTEGER
                   ACCESS  read-write
                   STATUS  mandatory
                   DESCRIPTION
                           "Check points the accounting database. This
                           mib variable must be read and then set with
                           the same value for the check point to
                           succeed. The value read and then set will be
                           incremented after a successful set request"
                   ::= { lip 11 }

               ipNoaccess OBJECT-TYPE
                   SYNTAX  Counter
                   ACCESS  read-only
                   STATUS  mandatory
                   DESCRIPTION
                           "Total number of packets dropped due to
                           access control failure."
                   ::= { lip 12 }


               -- Local TCP Group

          -- This group is present in all products which are using the
          -- TCP protocol.






          -- cisco MIB                                         [Page 63]
--





          -- Request for Comments: Draft             cisco Systems, Inc.


          -- Local TCP Connection Table

          -- This group provides additional objects to the table defined
          -- by RFC1156.

               ltcpConnTable OBJECT-TYPE
                   SYNTAX  SEQUENCE OF LTcpConnEntry
                   ACCESS  not-accessible
                   STATUS  mandatory
                   DESCRIPTION
                            "A list of TCP connection entries."
                   ::= { ltcp 1 }

               ltcpConnEntry OBJECT-TYPE
                   SYNTAX LTcpConnEntry
                   ACCESS  not-accessible
                   STATUS  mandatory
                   DESCRIPTION
                            "A collection of additional objects in the
                            cisco TCP implementation."
                   INDEX { tcpConnLocalAddress, tcpConnLocalPort,
                   tcpConnRemAddress, tcpConnRemPort }
               ::= { ltcpConnTable 1 }

               LTcpConnEntry ::=
                   SEQUENCE {
                       loctcpConnInBytes
                           INTEGER,
                       loctcpConnOutBytes
                           INTEGER,
                       loctcpConnInPkts
                           INTEGER,
                       loctcpConnOutPkts
                           INTEGER,
                       loctcpConnElapsed
                           TimeTicks
                   }


          -- The following section describes the components of the
          -- table.

               loctcpConnInBytes OBJECT-TYPE
                   SYNTAX  INTEGER
                   ACCESS  read-only





          -- cisco MIB                                         [Page 64]
--





          -- Request for Comments: Draft             cisco Systems, Inc.


                   STATUS  mandatory
                   DESCRIPTION
                           "Bytes input for this TCP connection."
                   ::= { ltcpConnEntry 1 }

               loctcpConnOutBytes OBJECT-TYPE
                   SYNTAX  INTEGER
                   ACCESS  read-only
                   STATUS  mandatory
                   DESCRIPTION
                           "Bytes output for this TCP connection."
                   ::= { ltcpConnEntry 2 }

               loctcpConnInPkts OBJECT-TYPE
                   SYNTAX  INTEGER
                   ACCESS  read-only
                   STATUS  mandatory
                   DESCRIPTION
                           "Packets input for this TCP connection."
                   ::= { ltcpConnEntry 3 }

               loctcpConnOutPkts OBJECT-TYPE
                   SYNTAX  INTEGER
                   ACCESS  read-only
                   STATUS  mandatory
                   DESCRIPTION
                           "Packets output for this TCP connection."
                   ::= { ltcpConnEntry 4 }

               loctcpConnElapsed OBJECT-TYPE
                   SYNTAX  TimeTicks
                   ACCESS  read-only
                   STATUS  mandatory
                   DESCRIPTION
                           "How long this TCP connection has been
                           established."
                   ::= { ltcpConnEntry 5 }

               -- End of table



               -- Local cisco Terminal Server Group







          -- cisco MIB                                         [Page 65]
--





          -- Request for Comments: Draft             cisco Systems, Inc.


          -- This group is present in all products which contain
          -- asynchronous terminal lines.

               tsLines OBJECT-TYPE
                   SYNTAX  INTEGER
                   ACCESS  read-only
                   STATUS  mandatory
                   DESCRIPTION
                           "Number of terminal lines on this device.
                           Includes virtual lines."
                   ::= { lts 1 }


               -- Local Terminal Server Line Table

          -- This group contains terminal server specific
          -- information on a per line basis.

               ltsLineTable OBJECT-TYPE
                   SYNTAX  SEQUENCE OF LTsLineEntry
                   ACCESS  not-accessible
                   STATUS  mandatory
                   DESCRIPTION
                            "A list of terminal server line entries."
                   ::= { lts 2 }

               ltsLineEntry OBJECT-TYPE
                   SYNTAX LTsLineEntry
                   ACCESS  not-accessible
                   STATUS  mandatory
                   DESCRIPTION
                            "A collection of per TTY objects in the
                            cisco Terminal Server implementation."
                   INDEX { tsLineNum }
               ::= { ltsLineTable 1 }

               LTsLineEntry ::=
                   SEQUENCE {
                       tsLineActive
                           INTEGER,
                       tsLineType
                           INTEGER,
                       tsLineAutobaud
                           INTEGER,
                       tsLineSpeedin





          -- cisco MIB                                         [Page 66]
--





          -- Request for Comments: Draft             cisco Systems, Inc.


                           INTEGER,
                       tsLineSpeedout
                           INTEGER,
                       tsLineFlow
                           INTEGER,
                       tsLineModem
                           INTEGER,
                       tsLineLoc
                           DisplayString,
                       tsLineTerm
                           DisplayString,
                       tsLineScrlen
                           INTEGER,
                       tsLineScrwid
                           INTEGER,
                       tsLineEsc
                           DisplayString,
                       tsLineTmo
                           INTEGER,
                       tsLineSestmo
                           INTEGER,
                       tsLineRotary
                           INTEGER,
                       tsLineUses
                           INTEGER,
                       tsLineNses
                           INTEGER,
                       tsLineUser
                           DisplayString,
                       tsLineNoise
                           INTEGER,
                       tsLineNum
                           INTEGER
                   }


          -- The following section describes the components of the
          -- table.

               tsLineActive OBJECT-TYPE
                   SYNTAX  INTEGER
                   ACCESS  read-only
                   STATUS  mandatory
                   DESCRIPTION
                           "Boolean whether this line is active or not."
                   ::= { ltsLineEntry 1 }






          -- cisco MIB                                         [Page 67]
--





          -- Request for Comments: Draft             cisco Systems, Inc.


               tsLineType OBJECT-TYPE
                   SYNTAX  INTEGER {
                        unknown(1),
                        console(2),
                        terminal(3),
                        line-printer(4),
                        virtual-terminal(5),
                        auxiliary(6)
                   }
                   ACCESS  read-only
                   STATUS  mandatory
                   DESCRIPTION
                           "Type of line."
                   ::= { ltsLineEntry 2 }

               tsLineAutobaud OBJECT-TYPE
                   SYNTAX  INTEGER
                   ACCESS  read-only
                   STATUS  mandatory
                   DESCRIPTION
                           "Boolean whether line will autobaud or not."
                   ::= { ltsLineEntry 3 }

               tsLineSpeedin OBJECT-TYPE
                   SYNTAX  INTEGER
                   ACCESS  read-only
                   STATUS  mandatory
                   DESCRIPTION
                           "What input speed the line is running at."
                   ::= { ltsLineEntry 4 }

               tsLineSpeedout OBJECT-TYPE
                   SYNTAX  INTEGER
                   ACCESS  read-only
                   STATUS  mandatory
                   DESCRIPTION
                           "What output speed the line is running at."
                   ::= { ltsLineEntry 5 }

               tsLineFlow OBJECT-TYPE
                   SYNTAX  INTEGER {
                        unknown(1),
                        none(2),
                        software-input(3),
                        software-output(4),





          -- cisco MIB                                         [Page 68]
--





          -- Request for Comments: Draft             cisco Systems, Inc.


                        software-both(5),
                        hardware-input(6),
                        hardware-output(7),
                        hardware-both(8)
                   }
                   ACCESS  read-only
                   STATUS  mandatory
                   DESCRIPTION
                           "What kind of flow control the line is
                           using."
                   ::= { ltsLineEntry 6 }

               tsLineModem OBJECT-TYPE
                   SYNTAX  INTEGER {
                        unknown(1),
                        none(2),
                        call-in(3),
                        call-out(4),
                        cts-required(5),
                        ri-is-cd(6),
                        inout(7)
                   }
                   ACCESS  read-only
                   STATUS  mandatory
                   DESCRIPTION
                           "What kind of modem control the line is
                           using."
                   ::= { ltsLineEntry 7 }

               tsLineLoc OBJECT-TYPE
                   SYNTAX  DisplayString
                   ACCESS  read-only
                   STATUS  mandatory
                   DESCRIPTION
                           "Describes the line's physical location."
                   ::= { ltsLineEntry 8 }

               tsLineTerm OBJECT-TYPE
                   SYNTAX  DisplayString
                   ACCESS  read-only
                   STATUS  mandatory
                   DESCRIPTION
                           "Describes the line's terminal type."
                   ::= { ltsLineEntry 9 }






          -- cisco MIB                                         [Page 69]
--





          -- Request for Comments: Draft             cisco Systems, Inc.


               tsLineScrlen OBJECT-TYPE
                   SYNTAX  INTEGER
                   ACCESS  read-only
                   STATUS  mandatory
                   DESCRIPTION
                           "Length in lines of the screen of terminal
                           attached to this line."
                   ::= { ltsLineEntry 10 }

               tsLineScrwid OBJECT-TYPE
                   SYNTAX  INTEGER
                   ACCESS  read-only
                   STATUS  mandatory
                   DESCRIPTION
                           "Width in characters of the screen of
                           terminal attached to this line."
                   ::= { ltsLineEntry 11 }

               tsLineEsc OBJECT-TYPE
                   SYNTAX  DisplayString
                   ACCESS  read-only
                   STATUS  mandatory
                   DESCRIPTION
                           "Escape character used to break out of active
                           sessions."
                   ::= { ltsLineEntry 12 }

               tsLineTmo OBJECT-TYPE
                   SYNTAX  INTEGER
                   ACCESS  read-only
                   STATUS  mandatory
                   DESCRIPTION
                           "Line idleness timeout in seconds."
                   ::= { ltsLineEntry 13 }

               tsLineSestmo OBJECT-TYPE
                   SYNTAX  INTEGER
                   ACCESS  read-only
                   STATUS  mandatory
                   DESCRIPTION
                           "Session idleness timeout in seconds."
                   ::= { ltsLineEntry 14 }

               tsLineRotary OBJECT-TYPE
                   SYNTAX  INTEGER





          -- cisco MIB                                         [Page 70]
--





          -- Request for Comments: Draft             cisco Systems, Inc.


                   ACCESS  read-only
                   STATUS  mandatory
                   DESCRIPTION
                           "Rotary group number the line belongs in."
                   ::= { ltsLineEntry 15 }

               tsLineUses OBJECT-TYPE
                   SYNTAX  INTEGER
                   ACCESS  read-only
                   STATUS  mandatory
                   DESCRIPTION
                           "Number of times a connection has been made
                           to or from this line."
                   ::= { ltsLineEntry 16 }

               tsLineNses OBJECT-TYPE
                   SYNTAX  INTEGER
                   ACCESS  read-only
                   STATUS  mandatory
                   DESCRIPTION
                           "Current number of sessions in use on this
                           line."
                   ::= { ltsLineEntry 17 }

               tsLineUser OBJECT-TYPE
                   SYNTAX  DisplayString
                   ACCESS  read-only
                   STATUS  mandatory
                   DESCRIPTION
                           "TACACS user name, if TACACS enabled, of user
                           on this line."
                   ::= { ltsLineEntry 18 }

               tsLineNoise OBJECT-TYPE
                   SYNTAX  INTEGER
                   ACCESS  read-only
                   STATUS  mandatory
                   DESCRIPTION
                           "Count of garbage characters received when
                           line inactive."
                   ::= { ltsLineEntry 19 }

               tsLineNum OBJECT-TYPE
                   SYNTAX  INTEGER
                   ACCESS  not-accessible
                   STATUS  mandatory
                   DESCRIPTION
                           "The line number (table index)."
                   ::= { ltsLineEntry 20 }

               -- End of table







          -- cisco MIB                                         [Page 71]
--





          -- Request for Comments: Draft             cisco Systems, Inc.


               -- Local Terminal Server Line Session Table

          -- This group contains terminal server specific
          -- information on a per line and per session basis.

               ltsLineSessionTable OBJECT-TYPE
                   SYNTAX  SEQUENCE OF LTsLineSessionEntry
                   ACCESS  not-accessible
                   STATUS  mandatory
                   DESCRIPTION
                            "A list of terminal server line and session
                            entries."
                   ::= { lts 3 }

               ltsLineSessionEntry OBJECT-TYPE
                   SYNTAX LTsLineSessionEntry
                   ACCESS  not-accessible
                   STATUS  mandatory
                   DESCRIPTION
                            "A collection of per session and per TTY
                            objects in the cisco Terminal Server
                            implementation."
                   INDEX { tslineSesLine, tslineSesSession }
               ::= { ltsLineSessionTable 1 }

               LTsLineSessionEntry ::=
                   SEQUENCE {
                       tslineSesType
                           INTEGER,
                       tslineSesDir
                           INTEGER,
                       tslineSesAddr
                           IpAddress,
                       tslineSesName
                           DisplayString,
                       tslineSesCur
                           INTEGER,
                       tslineSesIdle
                           INTEGER,
                       tslineSesLine
                           INTEGER,
                       tslineSesSession
                           INTEGER
                   }


          -- The following section describes the components of the
          -- table.






          -- cisco MIB                                         [Page 72]
--





          -- Request for Comments: Draft             cisco Systems, Inc.


               tslineSesType OBJECT-TYPE
                   SYNTAX  INTEGER {
                        unknown(1),
                        pad(2),
                        stream(3),
                        rlogin(4),
                        telnet(5),
                        tcp(6),
                        lat(7),
                        mop(8),
                        slip(9),
                        xremote(10),
			rshell(11)
                   }
                   ACCESS  read-only
                   STATUS  mandatory
                   DESCRIPTION
                           "Type of session."
                   ::= { ltsLineSessionEntry 1 }

               tslineSesDir OBJECT-TYPE
                   SYNTAX  INTEGER {
                        unknown(1),
                        incoming(2),
                        outgoing(3)
                   }
                   ACCESS  read-only
                   STATUS  mandatory
                   DESCRIPTION
                           "Direction of session."
                   ::= { ltsLineSessionEntry 2 }

               tslineSesAddr OBJECT-TYPE
                   SYNTAX  IpAddress
                   ACCESS  read-only
                   STATUS  mandatory
                   DESCRIPTION
                           "Remote host address of session. [What about
                           PAD connections?]"
                   ::= { ltsLineSessionEntry 3 }

               tslineSesName OBJECT-TYPE
                   SYNTAX  DisplayString
                   ACCESS  read-only
                   STATUS  mandatory
                   DESCRIPTION





          -- cisco MIB                                         [Page 73]
--





          -- Request for Comments: Draft             cisco Systems, Inc.


                           "Remote host name of session."
                   ::= { ltsLineSessionEntry 4 }

               tslineSesCur OBJECT-TYPE
                   SYNTAX  INTEGER
                   ACCESS  read-only
                   STATUS  mandatory
                   DESCRIPTION
                           "Boolean whether session is the currently
                           active one."
                   ::= { ltsLineSessionEntry 5 }

               tslineSesIdle OBJECT-TYPE
                   SYNTAX  INTEGER
                   ACCESS  read-only
                   STATUS  mandatory
                   DESCRIPTION
                           "Time in seconds session has been idle."
                   ::= { ltsLineSessionEntry 6 }

               tslineSesLine OBJECT-TYPE
                   SYNTAX  INTEGER
                   ACCESS  not-accessible
                   STATUS  mandatory
                   DESCRIPTION
                           "The line number (primary index)."
                   ::= { ltsLineSessionEntry 7 }

               tslineSesSession OBJECT-TYPE
                   SYNTAX  INTEGER
                   ACCESS  not-accessible
                   STATUS  mandatory
                   DESCRIPTION
                           "The session number (secondary index)."
                   ::= { ltsLineSessionEntry 8 }

               -- End of table


               tsMsgTtyLine OBJECT-TYPE
                   SYNTAX  INTEGER
                   ACCESS  read-write
                   STATUS  mandatory
                   DESCRIPTION
                           "tty line to send the message to. -1 will
                           send it to all tty lines"
                   ::= { lts 4 }

               tsMsgIntervaltim OBJECT-TYPE
                   SYNTAX  INTEGER
                   ACCESS  read-write
                   STATUS  mandatory
                   DESCRIPTION
                           "Interval between reissuing message in
                           milliseconds. Minimum non-zero setting is
                           10000. 0 will cause the routine to choose its
                           own intervals becoming more frequent as
                           MessageDuration gets close to expiring. 2hr,
                           1hr, 30min, 5min, 1min"
                   ::= { lts 5 }






          -- cisco MIB                                         [Page 74]
--





          -- Request for Comments: Draft             cisco Systems, Inc.


               tsMsgDuration OBJECT-TYPE
                   SYNTAX  INTEGER
                   ACCESS  read-write
                   STATUS  mandatory
                   DESCRIPTION
                           "Length of time to reissue message in
                           milliseconds. Minimum non-zero setting is
                           10000. A setting of 0 will not repeat the
                           message."
                   ::= { lts 6 }

               tsMsgText OBJECT-TYPE
                   SYNTAX  DisplayString
                   ACCESS  read-write
                   STATUS  mandatory
                   DESCRIPTION
                           "Up to 256 characters that will make up the
                           message"
                   ::= { lts 7 }

               tsMsgTmpBanner OBJECT-TYPE
                   SYNTAX  INTEGER {
                        no(1),
                        additive(2)
                   }
                   ACCESS  read-write
                   STATUS  mandatory
                   DESCRIPTION
                           "Should the message be used as a temporary
                           banner. 1 - No. 2 - In addition to the normal
                           banner"
                   ::= { lts 8 }

               tsMsgSend OBJECT-TYPE
                   SYNTAX  INTEGER {
                        nothing(1),
                        reload(2),
                        messagedone(3),
                        abort(4)
                   }
                   ACCESS  read-write
                   STATUS  mandatory
                   DESCRIPTION
                           "Sends the message. The value determines what
                           to do after the message has completed."





          -- cisco MIB                                         [Page 75]
--





          -- Request for Comments: Draft             cisco Systems, Inc.


                   ::= { lts 9 }


               -- Local cisco Flash Group

          -- This group is present in all products which contain flash"

               flashSize OBJECT-TYPE
                   SYNTAX  INTEGER
                   ACCESS  read-only
                   STATUS  mandatory
                   DESCRIPTION
                           "Total Size in Octets of Flash memory"
                   ::= { lflash 1 }

               flashFree OBJECT-TYPE
                   SYNTAX  INTEGER
                   ACCESS  read-only
                   STATUS  mandatory
                   DESCRIPTION
                           "Unused Size in Octets of Flash memory"
                   ::= { lflash 2 }

               flashController OBJECT-TYPE
                   SYNTAX  DisplayString
                   ACCESS  read-only
                   STATUS  mandatory
                   DESCRIPTION
                           "flash controller"
                   ::= { lflash 3 }

               flashCard OBJECT-TYPE
                   SYNTAX  DisplayString
                   ACCESS  read-only
                   STATUS  mandatory
                   DESCRIPTION
                           "flash card"
                   ::= { lflash 4 }

               flashVPP OBJECT-TYPE
                   SYNTAX  INTEGER {
                        installed(1),
                        missing(2)
                   }
                   ACCESS  read-only





          -- cisco MIB                                         [Page 76]
--





          -- Request for Comments: Draft             cisco Systems, Inc.


                   STATUS  mandatory
                   DESCRIPTION
                           "State of the VPP DIP"
                   ::= { lflash 5 }

               flashErase OBJECT-TYPE
                   SYNTAX  INTEGER
                   ACCESS  write-only
                   STATUS  mandatory
                   DESCRIPTION
                           "Request to erase flash memory"
                   ::= { lflash 6 }

               flashEraseTime OBJECT-TYPE
                   SYNTAX  TimeTicks
                   ACCESS  read-only
                   STATUS  mandatory
                   DESCRIPTION
                           "Last time the flash was erased"
                   ::= { lflash 7 }

               flashEraseStatus OBJECT-TYPE
                   SYNTAX  INTEGER {
                        flashOpInProgress(1),
                        flashOpSuccess(2),
                        flashOpFailure(3),
                        flashReadOnly(4),
                        flashOpenFailure(5),
                        bufferAllocationFailure(6)
                   }
                   ACCESS  read-only
                   STATUS  mandatory
                   DESCRIPTION
                           "Status of current or last flash erasing"
                   ::= { lflash 8 }

               flashToNet OBJECT-TYPE
                   SYNTAX  DisplayString
                   ACCESS  write-only
                   STATUS  mandatory
                   DESCRIPTION
                           "Write flash entry to tftp server. Value
                           should be the name of the flash entry to
                           send. Instance is the IP address of the tftp
                           host."





          -- cisco MIB                                         [Page 77]
--





          -- Request for Comments: Draft             cisco Systems, Inc.


                   ::= { lflash 9 }

               flashToNetTime OBJECT-TYPE
                   SYNTAX  TimeTicks
                   ACCESS  read-only
                   STATUS  mandatory
                   DESCRIPTION
                           "Last time a copy from the flash to the net
                           took place"
                   ::= { lflash 10 }

               flashToNetStatus OBJECT-TYPE
                   SYNTAX  INTEGER {
                        flashOpInProgress(1),
                        flashOpSuccess(2),
                        flashOpFailure(3),
                        flashReadOnly(4),
                        flashOpenFailure(5),
                        bufferAllocationFailure(6)
                   }
                   ACCESS  read-only
                   STATUS  mandatory
                   DESCRIPTION
                           "Status of current or last flash to net
                           transfer"
                   ::= { lflash 11 }

               netToFlash OBJECT-TYPE
                   SYNTAX  DisplayString
                   ACCESS  write-only
                   STATUS  mandatory
                   DESCRIPTION
                           "Write flash entry from tftp server. Value
                           should be the name of the flash entry to
                           write. Instance is the IP address of the tftp
                           host."
                   ::= { lflash 12 }

               netToFlashTime OBJECT-TYPE
                   SYNTAX  TimeTicks
                   ACCESS  read-only
                   STATUS  mandatory
                   DESCRIPTION
                           "Last time a copy from the net to the flash
                           took place"





          -- cisco MIB                                         [Page 78]
--





          -- Request for Comments: Draft             cisco Systems, Inc.


                   ::= { lflash 13 }

               netToFlashStatus OBJECT-TYPE
                   SYNTAX  INTEGER {
                        flashOpInProgress(1),
                        flashOpSuccess(2),
                        flashOpFailure(3),
                        flashReadOnly(4),
                        flashOpenFailure(5),
                        bufferAllocationFailure(6)
                   }
                   ACCESS  read-only
                   STATUS  mandatory
                   DESCRIPTION
                           "Status of current or last net to flash
                           transfer"
                   ::= { lflash 14 }

               flashStatus OBJECT-TYPE
                   SYNTAX  INTEGER {
                        busy(1),
                        available(2)
                   }
                   ACCESS  read-only
                   STATUS  mandatory
                   DESCRIPTION
                           "Status of the availablity of flash"
                   ::= { lflash 15 }

               flashEntries OBJECT-TYPE
                   SYNTAX  INTEGER
                   ACCESS  read-only
                   STATUS  mandatory
                   DESCRIPTION
                           "Number of entries in the flash directory"
                   ::= { lflash 16 }


               -- Local Flash file Table

          -- This group contains information on a per file basis

               lflashFileDirTable OBJECT-TYPE
                   SYNTAX  SEQUENCE OF LFlashFileDirEntry
                   ACCESS  not-accessible





          -- cisco MIB                                         [Page 79]
--





          -- Request for Comments: Draft             cisco Systems, Inc.


                   STATUS  mandatory
                   DESCRIPTION
                            " A list of flash file entries."
                   ::= { lflash 17 }

               lflashFileDirEntry OBJECT-TYPE
                   SYNTAX LFlashFileDirEntry
                   ACCESS  not-accessible
                   STATUS  mandatory
                   DESCRIPTION
                            "A collection of flash eprom objects"
                   INDEX { flashEntries }
               ::= { lflashFileDirTable 1 }

               LFlashFileDirEntry ::=
                   SEQUENCE {
                       flashDirName
                           DisplayString,
                       flashDirSize
                           INTEGER,
                       flashDirStatus
                           INTEGER
                   }


          -- The following section describes the components of the
          -- table.

               flashDirName OBJECT-TYPE
                   SYNTAX  DisplayString
                   ACCESS  read-only
                   STATUS  mandatory
                   DESCRIPTION
                           "Name associated with the flash entry"
                   ::= { lflashFileDirEntry 1 }

               flashDirSize OBJECT-TYPE
                   SYNTAX  INTEGER
                   ACCESS  read-only
                   STATUS  mandatory
                   DESCRIPTION
                           "Size in Octets of a flash entry"
                   ::= { lflashFileDirEntry 2 }

               flashDirStatus OBJECT-TYPE





          -- cisco MIB                                         [Page 80]
--





          -- Request for Comments: Draft             cisco Systems, Inc.


                   SYNTAX  INTEGER {
                        valid(1),
                        deleted(2)
                   }
                   ACCESS  read-only
                   STATUS  mandatory
                   DESCRIPTION
                           "Indicates the status of the entry"
                   ::= { lflashFileDirEntry 3 }

               -- End of table



               -- Temporary Variable Section

          -- This section is equivalent to the experimental
          -- space defined by the SMI. It contains variables
          -- that are useful to have but are beyond cisco's
          -- ability to control and maintain. This section can
          -- change from release to release without warning.
          -- This document controls what is contained here for
          -- this version.


          -- Temporary DECNET Section

          -- This group is present in all router based products.

               dnForward OBJECT-TYPE
                   SYNTAX  INTEGER
                   ACCESS  read-only
                   STATUS  mandatory
                   DESCRIPTION
                           "Total count of DECNET packets forwarded."
                   ::= { tmpdecnet 1 }

               dnReceived OBJECT-TYPE
                   SYNTAX  INTEGER
                   ACCESS  read-only
                   STATUS  mandatory
                   DESCRIPTION
                           "Count of total DECNET packets received."
                   ::= { tmpdecnet 2 }






          -- cisco MIB                                         [Page 81]
--





          -- Request for Comments: Draft             cisco Systems, Inc.


               dnFormaterr OBJECT-TYPE
                   SYNTAX  INTEGER
                   ACCESS  read-only
                   STATUS  mandatory
                   DESCRIPTION
                           "Total number of DECNET packets received with
                           header errors."
                   ::= { tmpdecnet 3 }

               dnNotgateway OBJECT-TYPE
                   SYNTAX  INTEGER
                   ACCESS  read-only
                   STATUS  mandatory
                   DESCRIPTION
                           "Total number of packets received while not
                           routing."
                   ::= { tmpdecnet 4 }

               dnNotimp OBJECT-TYPE
                   SYNTAX  INTEGER
                   ACCESS  read-only
                   STATUS  mandatory
                   DESCRIPTION
                           "Total number of unknown control packets
                           received."
                   ::= { tmpdecnet 5 }

               dnHellos OBJECT-TYPE
                   SYNTAX  INTEGER
                   ACCESS  read-only
                   STATUS  mandatory
                   DESCRIPTION
                           "Total number of Hellos received."
                   ::= { tmpdecnet 6 }

               dnBadhello OBJECT-TYPE
                   SYNTAX  INTEGER
                   ACCESS  read-only
                   STATUS  mandatory
                   DESCRIPTION
                           "Total number of received bad Hellos."
                   ::= { tmpdecnet 7 }

               dnNotlong OBJECT-TYPE
                   SYNTAX  INTEGER





          -- cisco MIB                                         [Page 82]
--





          -- Request for Comments: Draft             cisco Systems, Inc.


                   ACCESS  read-only
                   STATUS  mandatory
                   DESCRIPTION
                           "Total number of received packets not in long
                           format."
                   ::= { tmpdecnet 8 }

               dnDatas OBJECT-TYPE
                   SYNTAX  INTEGER
                   ACCESS  read-only
                   STATUS  mandatory
                   DESCRIPTION
                           "Total number of received data packets."
                   ::= { tmpdecnet 9 }

               dnBigaddr OBJECT-TYPE
                   SYNTAX  INTEGER
                   ACCESS  read-only
                   STATUS  mandatory
                   DESCRIPTION
                           "Total number of too large addresses."
                   ::= { tmpdecnet 10 }

               dnNoroute OBJECT-TYPE
                   SYNTAX  INTEGER
                   ACCESS  read-only
                   STATUS  mandatory
                   DESCRIPTION
                           "Total number of packets dropped due to no
                           route present."
                   ::= { tmpdecnet 11 }

               dnNoencap OBJECT-TYPE
                   SYNTAX  INTEGER
                   ACCESS  read-only
                   STATUS  mandatory
                   DESCRIPTION
                           "Total number of packets dropped due to
                           output encapsulation failure."
                   ::= { tmpdecnet 12 }

               dnLevel1s OBJECT-TYPE
                   SYNTAX  INTEGER
                   ACCESS  read-only
                   STATUS  mandatory





          -- cisco MIB                                         [Page 83]
--





          -- Request for Comments: Draft             cisco Systems, Inc.


                   DESCRIPTION
                           "Total number of Level 1 routing packets
                           received."
                   ::= { tmpdecnet 13 }

               dnBadlevel1 OBJECT-TYPE
                   SYNTAX  INTEGER
                   ACCESS  read-only
                   STATUS  mandatory
                   DESCRIPTION
                           "Total number of bad Level 1 routing packets
                           received."
                   ::= { tmpdecnet 14 }

               dnToomanyhops OBJECT-TYPE
                   SYNTAX  INTEGER
                   ACCESS  read-only
                   STATUS  mandatory
                   DESCRIPTION
                           "Total number of packets received which
                           visited too many nodes."
                   ::= { tmpdecnet 15 }

               dnHellosent OBJECT-TYPE
                   SYNTAX  INTEGER
                   ACCESS  read-only
                   STATUS  mandatory
                   DESCRIPTION
                           "Total number of Hellos output."
                   ::= { tmpdecnet 16 }

               dnLevel1sent OBJECT-TYPE
                   SYNTAX  INTEGER
                   ACCESS  read-only
                   STATUS  mandatory
                   DESCRIPTION
                           "Total number of Level 1 routing packets
                           sent."
                   ::= { tmpdecnet 17 }

               dnNomemory OBJECT-TYPE
                   SYNTAX  INTEGER
                   ACCESS  read-only
                   STATUS  mandatory
                   DESCRIPTION





          -- cisco MIB                                         [Page 84]
--





          -- Request for Comments: Draft             cisco Systems, Inc.


                           "Total number of memory requests denied."
                   ::= { tmpdecnet 18 }

               dnOtherhello OBJECT-TYPE
                   SYNTAX  INTEGER
                   ACCESS  read-only
                   STATUS  mandatory
                   DESCRIPTION
                           "Total number of Hellos received from another
                           area."
                   ::= { tmpdecnet 19 }

               dnOtherlevel1 OBJECT-TYPE
                   SYNTAX  INTEGER
                   ACCESS  read-only
                   STATUS  mandatory
                   DESCRIPTION
                           "Total number of Level 1 routing packets
                           received from another area."
                   ::= { tmpdecnet 20 }

               dnLevel2s OBJECT-TYPE
                   SYNTAX  INTEGER
                   ACCESS  read-only
                   STATUS  mandatory
                   DESCRIPTION
                           "Total number of Level 2 routing packets
                           received."
                   ::= { tmpdecnet 21 }

               dnLevel2sent OBJECT-TYPE
                   SYNTAX  INTEGER
                   ACCESS  read-only
                   STATUS  mandatory
                   DESCRIPTION
                           "Total number of Level 2 routing packets
                           sent."
                   ::= { tmpdecnet 22 }

               dnNovector OBJECT-TYPE
                   SYNTAX  INTEGER
                   ACCESS  read-only
                   STATUS  mandatory
                   DESCRIPTION
                           "Total number of missing routing vectors."





          -- cisco MIB                                         [Page 85]
--





          -- Request for Comments: Draft             cisco Systems, Inc.


                   ::= { tmpdecnet 23 }

               dnOtherlevel2 OBJECT-TYPE
                   SYNTAX  INTEGER
                   ACCESS  read-only
                   STATUS  mandatory
                   DESCRIPTION
                           "Total number of received Level 2 routing
                           packets from another area."
                   ::= { tmpdecnet 24 }

               dnNoaccess OBJECT-TYPE
                   SYNTAX  INTEGER
                   ACCESS  read-only
                   STATUS  mandatory
                   DESCRIPTION
                           "Total number of packets dropped due to
                           access control failure."
                   ::= { tmpdecnet 25 }

               dnAreaTable OBJECT-TYPE
                   SYNTAX  SEQUENCE OF DnAreaTableEntry
                   ACCESS  not-accessible
                   STATUS  mandatory
                   DESCRIPTION
                            "DECNET area routing table"
                   ::= { tmpdecnet 26 }

               dnAreaTableEntry OBJECT-TYPE
                   SYNTAX DnAreaTableEntry
                   ACCESS  not-accessible
                   STATUS  mandatory
                   DESCRIPTION
                            "DECNET area routing table"
                   INDEX { dnArea }
               ::= { dnAreaTable 1 }

               DnAreaTableEntry ::=
                   SEQUENCE {
                       dnArea
                           INTEGER,
                       dnACost
                           INTEGER,
                       dnAHop
                           INTEGER,





          -- cisco MIB                                         [Page 86]
--





          -- Request for Comments: Draft             cisco Systems, Inc.


                       dnAIfIndex
                           INTEGER,
                       dnANextHop
                           OCTET STRING,
                       dnAAge
                           INTEGER,
                       dnAPrio
                           INTEGER
                   }


          -- The following section describes the components of the
          -- table.

               dnArea OBJECT-TYPE
                   SYNTAX  INTEGER
                   ACCESS  read-only
                   STATUS  mandatory
                   DESCRIPTION
                           "DECNet area from the area table."
                   ::= { dnAreaTableEntry 1 }

               dnACost OBJECT-TYPE
                   SYNTAX  INTEGER
                   ACCESS  read-only
                   STATUS  mandatory
                   DESCRIPTION
                           "Cost of area in the area table."
                   ::= { dnAreaTableEntry 2 }

               dnAHop OBJECT-TYPE
                   SYNTAX  INTEGER
                   ACCESS  read-only
                   STATUS  mandatory
                   DESCRIPTION
                           "Number of hops to area in the area table."
                   ::= { dnAreaTableEntry 3 }

               dnAIfIndex OBJECT-TYPE
                   SYNTAX  INTEGER
                   ACCESS  read-only
                   STATUS  mandatory
                   DESCRIPTION
                           "Index of interface to the next hop address
                           to the area. 0 denotes self."





          -- cisco MIB                                         [Page 87]
--





          -- Request for Comments: Draft             cisco Systems, Inc.


                   ::= { dnAreaTableEntry 4 }

               dnANextHop OBJECT-TYPE
                   SYNTAX  OCTET STRING
                   ACCESS  read-only
                   STATUS  mandatory
                   DESCRIPTION
                           "Next hop DECNet address."
                   ::= { dnAreaTableEntry 5 }

               dnAAge OBJECT-TYPE
                   SYNTAX  INTEGER
                   ACCESS  read-only
                   STATUS  mandatory
                   DESCRIPTION
                           "Age in seconds of area route."
                   ::= { dnAreaTableEntry 6 }

               dnAPrio OBJECT-TYPE
                   SYNTAX  INTEGER
                   ACCESS  read-only
                   STATUS  mandatory
                   DESCRIPTION
                           "Priority of next hop router for area route."
                   ::= { dnAreaTableEntry 7 }

               -- End of table


               dnHostTable OBJECT-TYPE
                   SYNTAX  SEQUENCE OF DnHostTableEntry
                   ACCESS  not-accessible
                   STATUS  mandatory
                   DESCRIPTION
                            "DECNET routing table"
                   ::= { tmpdecnet 27 }

               dnHostTableEntry OBJECT-TYPE
                   SYNTAX DnHostTableEntry
                   ACCESS  not-accessible
                   STATUS  mandatory
                   DESCRIPTION
                            "DECNET routing table"
                   INDEX { dnHIdx1, dnHIdx2 }
               ::= { dnHostTable 1 }





          -- cisco MIB                                         [Page 88]
--





          -- Request for Comments: Draft             cisco Systems, Inc.


               DnHostTableEntry ::=
                   SEQUENCE {
                       dnHost
                           INTEGER,
                       dnHCost
                           INTEGER,
                       dnHHop
                           INTEGER,
                       dnHIfIndex
                           INTEGER,
                       dnHNextHop
                           OCTET STRING,
                       dnHAge
                           INTEGER,
                       dnHPrio
                           INTEGER,
                       dnHIdx1
                           INTEGER,
                       dnHIdx2
                           INTEGER
                   }


          -- The following section describes the components of the
          -- table.

               dnHost OBJECT-TYPE
                   SYNTAX  INTEGER
                   ACCESS  read-only
                   STATUS  mandatory
                   DESCRIPTION
                           "DECNet node address from the routing table."
                   ::= { dnHostTableEntry 1 }

               dnHCost OBJECT-TYPE
                   SYNTAX  INTEGER
                   ACCESS  read-only
                   STATUS  mandatory
                   DESCRIPTION
                           "Cost of path to node in the routing table."
                   ::= { dnHostTableEntry 2 }

               dnHHop OBJECT-TYPE
                   SYNTAX  INTEGER
                   ACCESS  read-only
                   STATUS  mandatory
                   DESCRIPTION
                           "Number of hops to node in the routing
                           table."





          -- cisco MIB                                         [Page 89]
--





          -- Request for Comments: Draft             cisco Systems, Inc.


                   ::= { dnHostTableEntry 3 }

               dnHIfIndex OBJECT-TYPE
                   SYNTAX  INTEGER
                   ACCESS  read-only
                   STATUS  mandatory
                   DESCRIPTION
                           "Index of interface to the next hop address
                           to the node. 0 denotes self."
                   ::= { dnHostTableEntry 4 }

               dnHNextHop OBJECT-TYPE
                   SYNTAX  OCTET STRING
                   ACCESS  read-only
                   STATUS  mandatory
                   DESCRIPTION
                           "Next hop DECNet address."
                   ::= { dnHostTableEntry 5 }

               dnHAge OBJECT-TYPE
                   SYNTAX  INTEGER
                   ACCESS  read-only
                   STATUS  mandatory
                   DESCRIPTION
                           "Age in seconds of route to node."
                   ::= { dnHostTableEntry 6 }

               dnHPrio OBJECT-TYPE
                   SYNTAX  INTEGER
                   ACCESS  read-only
                   STATUS  mandatory
                   DESCRIPTION
                           "Priority of next hop router for node."
                   ::= { dnHostTableEntry 7 }

               dnHIdx1 OBJECT-TYPE
                   SYNTAX  INTEGER
                   ACCESS  not-accessible
                   STATUS  mandatory
                   DESCRIPTION
                           "table index 1."
                   ::= { dnHostTableEntry 8 }

               dnHIdx2 OBJECT-TYPE
                   SYNTAX  INTEGER
                   ACCESS  not-accessible
                   STATUS  mandatory
                   DESCRIPTION
                           "table index 2."
                   ::= { dnHostTableEntry 9 }

               -- End of table


               dnIfTable OBJECT-TYPE
                   SYNTAX  SEQUENCE OF DnIfTableEntry
                   ACCESS  not-accessible
                   STATUS  mandatory
                   DESCRIPTION
                            "DECNET interface table"
                   ::= { tmpdecnet 28 }





          -- cisco MIB                                         [Page 90]
--





          -- Request for Comments: Draft             cisco Systems, Inc.


               dnIfTableEntry OBJECT-TYPE
                   SYNTAX DnIfTableEntry
                   ACCESS  not-accessible
                   STATUS  mandatory
                   DESCRIPTION
                            "DECNET interface table"
                   INDEX { ifIndex }
               ::= { dnIfTable 1 }

               DnIfTableEntry ::=
                   SEQUENCE {
                       dnIfCost
                           INTEGER
                   }


          -- The following section describes the components of the
          -- table.

               dnIfCost OBJECT-TYPE
                   SYNTAX  INTEGER
                   ACCESS  read-only
                   STATUS  mandatory
                   DESCRIPTION
                           "Cost of this interface."
                   ::= { dnIfTableEntry 1 }

               -- End of table



               -- Temporary XNS Section

          -- This group is present in all router based products.

               xnsInput OBJECT-TYPE
                   SYNTAX  INTEGER
                   ACCESS  read-only
                   STATUS  mandatory
                   DESCRIPTION
                           "Total input count of number of XNS packets."
                   ::= { tmpxns 1 }

               xnsLocal OBJECT-TYPE
                   SYNTAX  INTEGER





          -- cisco MIB                                         [Page 91]
--





          -- Request for Comments: Draft             cisco Systems, Inc.


                   ACCESS  read-only
                   STATUS  mandatory
                   DESCRIPTION
                           "Total count of XNS input packets for this
                           host."
                   ::= { tmpxns 2 }

               xnsBcastin OBJECT-TYPE
                   SYNTAX  INTEGER
                   ACCESS  read-only
                   STATUS  mandatory
                   DESCRIPTION
                           "Total count of number of XNS input broadcast
                           packets."
                   ::= { tmpxns 3 }

               xnsForward OBJECT-TYPE
                   SYNTAX  INTEGER
                   ACCESS  read-only
                   STATUS  mandatory
                   DESCRIPTION
                           "Total count of number of XNS packets
                           forwarded."
                   ::= { tmpxns 4 }

               xnsBcastout OBJECT-TYPE
                   SYNTAX  INTEGER
                   ACCESS  read-only
                   STATUS  mandatory
                   DESCRIPTION
                           "Total count of number of XNS output
                           broadcast packets."
                   ::= { tmpxns 5 }

               xnsErrin OBJECT-TYPE
                   SYNTAX  INTEGER
                   ACCESS  read-only
                   STATUS  mandatory
                   DESCRIPTION
                           "Total count of number of XNS Error input
                           packets."
                   ::= { tmpxns 6 }

               xnsErrout OBJECT-TYPE
                   SYNTAX  INTEGER





          -- cisco MIB                                         [Page 92]
--





          -- Request for Comments: Draft             cisco Systems, Inc.


                   ACCESS  read-only
                   STATUS  mandatory
                   DESCRIPTION
                           "Total count of number of XNS Error output
                           packets."
                   ::= { tmpxns 7 }

               xnsFormerr OBJECT-TYPE
                   SYNTAX  INTEGER
                   ACCESS  read-only
                   STATUS  mandatory
                   DESCRIPTION
                           "Total count of number of XNS input packets
                           with header errors."
                   ::= { tmpxns 8 }

               xnsChksum OBJECT-TYPE
                   SYNTAX  INTEGER
                   ACCESS  read-only
                   STATUS  mandatory
                   DESCRIPTION
                           "Total count of number of XNS input packets
                           with checksum errors."
                   ::= { tmpxns 9 }

               xnsNotgate OBJECT-TYPE
                   SYNTAX  INTEGER
                   ACCESS  read-only
                   STATUS  mandatory
                   DESCRIPTION
                           "Total count of number of XNS input packets
                           received while not routing."
                   ::= { tmpxns 10 }

               xnsHopcnt OBJECT-TYPE
                   SYNTAX  INTEGER
                   ACCESS  read-only
                   STATUS  mandatory
                   DESCRIPTION
                           "Total count of number of XNS input packets
                           that have exceeded the maximum hop count."
                   ::= { tmpxns 11 }

               xnsNoroute OBJECT-TYPE
                   SYNTAX  INTEGER





          -- cisco MIB                                         [Page 93]
--





          -- Request for Comments: Draft             cisco Systems, Inc.


                   ACCESS  read-only
                   STATUS  mandatory
                   DESCRIPTION
                           "Total count of number of XNS packets dropped
                           due to no route."
                   ::= { tmpxns 12 }

               xnsNoencap OBJECT-TYPE
                   SYNTAX  INTEGER
                   ACCESS  read-only
                   STATUS  mandatory
                   DESCRIPTION
                           "Total count of number of XNS packets dropped
                           due to output encapsulation failure."
                   ::= { tmpxns 13 }

               xnsOutput OBJECT-TYPE
                   SYNTAX  INTEGER
                   ACCESS  read-only
                   STATUS  mandatory
                   DESCRIPTION
                           "Total count of number of XNS output
                           packets."
                   ::= { tmpxns 14 }

               xnsInmult OBJECT-TYPE
                   SYNTAX  INTEGER
                   ACCESS  read-only
                   STATUS  mandatory
                   DESCRIPTION
                           "Total count of number of XNS input multicast
                           packets."
                   ::= { tmpxns 15 }

               xnsUnknown OBJECT-TYPE
                   SYNTAX  INTEGER
                   ACCESS  read-only
                   STATUS  mandatory
                   DESCRIPTION
                           "Total count of number of unknown XNS input
                           packets."
                   ::= { tmpxns 16 }

               xnsFwdbrd OBJECT-TYPE
                   SYNTAX  INTEGER





          -- cisco MIB                                         [Page 94]
--





          -- Request for Comments: Draft             cisco Systems, Inc.


                   ACCESS  read-only
                   STATUS  mandatory
                   DESCRIPTION
                           "Total count of number of XNS broadcast
                           packets forwarded."
                   ::= { tmpxns 17 }

               xnsEchoreqin OBJECT-TYPE
                   SYNTAX  INTEGER
                   ACCESS  read-only
                   STATUS  mandatory
                   DESCRIPTION
                           "Total count of number of XNS Echo request
                           packets received."
                   ::= { tmpxns 18 }

               xnsEchoreqout OBJECT-TYPE
                   SYNTAX  INTEGER
                   ACCESS  read-only
                   STATUS  mandatory
                   DESCRIPTION
                           "Total count of number of XNS Echo request
                           packets sent."
                   ::= { tmpxns 19 }

               xnsEchorepin OBJECT-TYPE
                   SYNTAX  INTEGER
                   ACCESS  read-only
                   STATUS  mandatory
                   DESCRIPTION
                           "Total count of number of XNS Echo reply
                           packets received."
                   ::= { tmpxns 20 }

               xnsEchorepout OBJECT-TYPE
                   SYNTAX  INTEGER
                   ACCESS  read-only
                   STATUS  mandatory
                   DESCRIPTION
                           "Total count of number of XNS Echo reply
                           packets sent."
                   ::= { tmpxns 21 }


               -- Temporary AppleTalk Section





          -- cisco MIB                                         [Page 95]
--





          -- Request for Comments: Draft             cisco Systems, Inc.


          -- This group is present in all router based products.

               atInput OBJECT-TYPE
                   SYNTAX  INTEGER
                   ACCESS  read-only
                   STATUS  mandatory
                   DESCRIPTION
                           "Total input count of number of AppleTalk
                           packets."
                   ::= { tmpappletalk 1 }

               atLocal OBJECT-TYPE
                   SYNTAX  INTEGER
                   ACCESS  read-only
                   STATUS  mandatory
                   DESCRIPTION
                           "Total count of AppleTalk input packets for
                           this host."
                   ::= { tmpappletalk 2 }

               atBcastin OBJECT-TYPE
                   SYNTAX  INTEGER
                   ACCESS  read-only
                   STATUS  mandatory
                   DESCRIPTION
                           "Total count of number of AppleTalk input
                           broadcast packets."
                   ::= { tmpappletalk 3 }

               atForward OBJECT-TYPE
                   SYNTAX  INTEGER
                   ACCESS  read-only
                   STATUS  mandatory
                   DESCRIPTION
                           "Total count of number of AppleTalk packets
                           forwarded."
                   ::= { tmpappletalk 4 }

               atBcastout OBJECT-TYPE
                   SYNTAX  INTEGER
                   ACCESS  read-only
                   STATUS  mandatory
                   DESCRIPTION
                           "Total count of number of AppleTalk output
                           broadcast packets."





          -- cisco MIB                                         [Page 96]
--





          -- Request for Comments: Draft             cisco Systems, Inc.


                   ::= { tmpappletalk 5 }

               atChksum OBJECT-TYPE
                   SYNTAX  INTEGER
                   ACCESS  read-only
                   STATUS  mandatory
                   DESCRIPTION
                           "Total count of number of AppleTalk input
                           packets with checksum erors."
                   ::= { tmpappletalk 7 }

               atNotgate OBJECT-TYPE
                   SYNTAX  INTEGER
                   ACCESS  read-only
                   STATUS  mandatory
                   DESCRIPTION
                           "Total count of AppleTalk input packets
                           received while not routing."
                   ::= { tmpappletalk 8 }

               atHopcnt OBJECT-TYPE
                   SYNTAX  INTEGER
                   ACCESS  read-only
                   STATUS  mandatory
                   DESCRIPTION
                           "Total count of number of AppleTalk input
                           packets that have exceeded the maximum hop
                           count."
                   ::= { tmpappletalk 9 }

               atNoaccess OBJECT-TYPE
                   SYNTAX  INTEGER
                   ACCESS  read-only
                   STATUS  mandatory
                   DESCRIPTION
                           "Total number of AppleTalk packets dropped
                           due to access control."
                   ::= { tmpappletalk 10 }

               atNoroute OBJECT-TYPE
                   SYNTAX  INTEGER
                   ACCESS  read-only
                   STATUS  mandatory
                   DESCRIPTION
                           "Total count of number of AppleTalk packets





          -- cisco MIB                                         [Page 97]
--





          -- Request for Comments: Draft             cisco Systems, Inc.


                           dropped due to no route."
                   ::= { tmpappletalk 11 }

               atNoencap OBJECT-TYPE
                   SYNTAX  INTEGER
                   ACCESS  read-only
                   STATUS  mandatory
                   DESCRIPTION
                           "Total count of number of AppleTalk packets
                           dropped due to output encapsulation failure."
                   ::= { tmpappletalk 12 }

               atOutput OBJECT-TYPE
                   SYNTAX  INTEGER
                   ACCESS  read-only
                   STATUS  mandatory
                   DESCRIPTION
                           "Total count of number of AppleTalk output
                           packets."
                   ::= { tmpappletalk 13 }

               atInmult OBJECT-TYPE
                   SYNTAX  INTEGER
                   ACCESS  read-only
                   STATUS  mandatory
                   DESCRIPTION
                           "Total count of number of AppleTalk input
                           multicast packets."
                   ::= { tmpappletalk 14 }

               atRtmpin OBJECT-TYPE
                   SYNTAX  INTEGER
                   ACCESS  read-only
                   STATUS  mandatory
                   DESCRIPTION
                           "Total count of number of AppleTalk RTMP
                           packets received."
                   ::= { tmpappletalk 15 }

               atRtmpout OBJECT-TYPE
                   SYNTAX  INTEGER
                   ACCESS  read-only
                   STATUS  mandatory
                   DESCRIPTION
                           "Total count of number of AppleTalk RTMP





          -- cisco MIB                                         [Page 98]
--





          -- Request for Comments: Draft             cisco Systems, Inc.


                           packets sent."
                   ::= { tmpappletalk 16 }

               atNbpin OBJECT-TYPE
                   SYNTAX  INTEGER
                   ACCESS  read-only
                   STATUS  mandatory
                   DESCRIPTION
                           "Total count of number of AppleTalk NBP
                           packets received."
                   ::= { tmpappletalk 17 }

               atNbpout OBJECT-TYPE
                   SYNTAX  INTEGER
                   ACCESS  read-only
                   STATUS  mandatory
                   DESCRIPTION
                           "Total count of number of AppleTalk NBP
                           packets sent."
                   ::= { tmpappletalk 18 }

               atAtp OBJECT-TYPE
                   SYNTAX  INTEGER
                   ACCESS  read-only
                   STATUS  mandatory
                   DESCRIPTION
                           "Total count of number of AppleTalk ATP
                           packets received."
                   ::= { tmpappletalk 19 }

               atZipin OBJECT-TYPE
                   SYNTAX  INTEGER
                   ACCESS  read-only
                   STATUS  mandatory
                   DESCRIPTION
                           "Total count of number of AppleTalk ZIP
                           packets received."
                   ::= { tmpappletalk 20 }

               atZipout OBJECT-TYPE
                   SYNTAX  INTEGER
                   ACCESS  read-only
                   STATUS  mandatory
                   DESCRIPTION
                           "Total count of number of AppleTalk ZIP





          -- cisco MIB                                         [Page 99]
--





          -- Request for Comments: Draft             cisco Systems, Inc.


                           packets sent."
                   ::= { tmpappletalk 21 }

               atEcho OBJECT-TYPE
                   SYNTAX  INTEGER
                   ACCESS  read-only
                   STATUS  mandatory
                   DESCRIPTION
                           "Total count of number of AppleTalk Echo
                           packets received."
                   ::= { tmpappletalk 22 }

               atEchoill OBJECT-TYPE
                   SYNTAX  INTEGER
                   ACCESS  read-only
                   STATUS  mandatory
                   DESCRIPTION
                           "Total count of number of illegal AppleTalk
                           Echo packets received."
                   ::= { tmpappletalk 23 }

               atDdpshort OBJECT-TYPE
                   SYNTAX  INTEGER
                   ACCESS  read-only
                   STATUS  mandatory
                   DESCRIPTION
                           "Total count of number of short AppleTalk DDP
                           packets received."
                   ::= { tmpappletalk 24 }

               atDdplong OBJECT-TYPE
                   SYNTAX  INTEGER
                   ACCESS  read-only
                   STATUS  mandatory
                   DESCRIPTION
                           "Total count of number of long AppleTalk DDP
                           packets received."
                   ::= { tmpappletalk 25 }

               atDdpbad OBJECT-TYPE
                   SYNTAX  INTEGER
                   ACCESS  read-only
                   STATUS  mandatory
                   DESCRIPTION
                           "Total count of number of illegal sized





          -- cisco MIB                                        [Page 100]
--





          -- Request for Comments: Draft             cisco Systems, Inc.


                           AppleTalk DDP packets received."
                   ::= { tmpappletalk 26 }

               atNobuffer OBJECT-TYPE
                   SYNTAX  INTEGER
                   ACCESS  read-only
                   STATUS  mandatory
                   DESCRIPTION
                           "Total count of number of AppleTalk packets
                           lost due to no memory."
                   ::= { tmpappletalk 27 }

               atArpreq OBJECT-TYPE
                   SYNTAX  INTEGER
                   ACCESS  read-only
                   STATUS  mandatory
                   DESCRIPTION
                           "Total count of number of input AppleTalk ARP
                           request packets."
                   ::= { tmpappletalk 28 }

               atArpreply OBJECT-TYPE
                   SYNTAX  INTEGER
                   ACCESS  read-only
                   STATUS  mandatory
                   DESCRIPTION
                           "Total count of number of AppleTalk ARP reply
                           packets output."
                   ::= { tmpappletalk 29 }

               atArpprobe OBJECT-TYPE
                   SYNTAX  INTEGER
                   ACCESS  read-only
                   STATUS  mandatory
                   DESCRIPTION
                           "Total count of number of input AppleTalk ARP
                           probe packets."
                   ::= { tmpappletalk 30 }

               atUnknown OBJECT-TYPE
                   SYNTAX  INTEGER
                   ACCESS  read-only
                   STATUS  mandatory
                   DESCRIPTION
                           "Total count of number of unknown AppleTalk





          -- cisco MIB                                        [Page 101]
--





          -- Request for Comments: Draft             cisco Systems, Inc.


                           input packets."
                   ::= { tmpappletalk 31 }


               -- Temporary Novell Section

          -- This group is present in all router based products.

               novellInput OBJECT-TYPE
                   SYNTAX  INTEGER
                   ACCESS  read-only
                   STATUS  mandatory
                   DESCRIPTION
                           "Total input count of number of NOVELL
                           packets."
                   ::= { tmpnovell 1 }

               novellBcastin OBJECT-TYPE
                   SYNTAX  INTEGER
                   ACCESS  read-only
                   STATUS  mandatory
                   DESCRIPTION
                           "Total count of number of NOVELL input
                           broadcast packets."
                   ::= { tmpnovell 2 }

               novellForward OBJECT-TYPE
                   SYNTAX  INTEGER
                   ACCESS  read-only
                   STATUS  mandatory
                   DESCRIPTION
                           "Total count of number of NOVELL packets
                           forwarded."
                   ::= { tmpnovell 3 }

               novellBcastout OBJECT-TYPE
                   SYNTAX  INTEGER
                   ACCESS  read-only
                   STATUS  mandatory
                   DESCRIPTION
                           "Total count of number of NOVELL output
                           broadcast packets."
                   ::= { tmpnovell 4 }

               novellFormerr OBJECT-TYPE





          -- cisco MIB                                        [Page 102]
--





          -- Request for Comments: Draft             cisco Systems, Inc.


                   SYNTAX  INTEGER
                   ACCESS  read-only
                   STATUS  mandatory
                   DESCRIPTION
                           "Total count of number of NOVELL input
                           packets with header errors."
                   ::= { tmpnovell 5 }

               novellChksum OBJECT-TYPE
                   SYNTAX  INTEGER
                   ACCESS  read-only
                   STATUS  mandatory
                   DESCRIPTION
                           "Total count of number of NOVELL input
                           packets with checksum erors."
                   ::= { tmpnovell 6 }

               novellHopcnt OBJECT-TYPE
                   SYNTAX  INTEGER
                   ACCESS  read-only
                   STATUS  mandatory
                   DESCRIPTION
                           "Total count of number of NOVELL input
                           packets that have exceeded the maximum hop
                           count."
                   ::= { tmpnovell 7 }

               novellNoroute OBJECT-TYPE
                   SYNTAX  INTEGER
                   ACCESS  read-only
                   STATUS  mandatory
                   DESCRIPTION
                           "Total count of number of NOVELL packets
                           dropped due to no route."
                   ::= { tmpnovell 8 }

               novellNoencap OBJECT-TYPE
                   SYNTAX  INTEGER
                   ACCESS  read-only
                   STATUS  mandatory
                   DESCRIPTION
                           "Total count of number of NOVELL packets
                           dropped due to output encapsulation failure."
                   ::= { tmpnovell 9 }






          -- cisco MIB                                        [Page 103]
--





          -- Request for Comments: Draft             cisco Systems, Inc.


               novellOutput OBJECT-TYPE
                   SYNTAX  INTEGER
                   ACCESS  read-only
                   STATUS  mandatory
                   DESCRIPTION
                           "Total count of number of NOVELL output
                           packets."
                   ::= { tmpnovell 10 }

               novellInmult OBJECT-TYPE
                   SYNTAX  INTEGER
                   ACCESS  read-only
                   STATUS  mandatory
                   DESCRIPTION
                           "Total count of number of NOVELL input
                           multicast packets."
                   ::= { tmpnovell 11 }

               novellLocal OBJECT-TYPE
                   SYNTAX  INTEGER
                   ACCESS  read-only
                   STATUS  mandatory
                   DESCRIPTION
                           "Total count of NOVELL input packets for this
                           host."
                   ::= { tmpnovell 12 }

               novellUnknown OBJECT-TYPE
                   SYNTAX  INTEGER
                   ACCESS  read-only
                   STATUS  mandatory
                   DESCRIPTION
                           "Total count of number of unknown NOVELL
                           input packets."
                   ::= { tmpnovell 13 }

               novellSapreqin OBJECT-TYPE
                   SYNTAX  INTEGER
                   ACCESS  read-only
                   STATUS  mandatory
                   DESCRIPTION
                           "Total count of number of NOVELL SAP request
                           packets received."
                   ::= { tmpnovell 14 }






          -- cisco MIB                                        [Page 104]
--





          -- Request for Comments: Draft             cisco Systems, Inc.


               novellSapresin OBJECT-TYPE
                   SYNTAX  INTEGER
                   ACCESS  read-only
                   STATUS  mandatory
                   DESCRIPTION
                           "Total count of number of NOVELL SAP response
                           packets received."
                   ::= { tmpnovell 15 }

               novellSapout OBJECT-TYPE
                   SYNTAX  INTEGER
                   ACCESS  read-only
                   STATUS  mandatory
                   DESCRIPTION
                           "Total count of number of NOVELL SAP request
                           packets sent."
                   ::= { tmpnovell 16 }

               novellSapreply OBJECT-TYPE
                   SYNTAX  INTEGER
                   ACCESS  read-only
                   STATUS  mandatory
                   DESCRIPTION
                           "Total count of number of NOVELL SAP reply
                           packets sent."
                   ::= { tmpnovell 17 }

               ipxActThresh OBJECT-TYPE
                   SYNTAX  INTEGER
                   ACCESS  read-only
                   STATUS  mandatory
                   DESCRIPTION
                           "Threshold of IPX accounting records in use
                           before IPX traffic will be unaccounted."
                   ::= { tmpnovell 18 }

               ipxActLostPkts OBJECT-TYPE
                   SYNTAX  INTEGER
                   ACCESS  read-only
                   STATUS  mandatory
                   DESCRIPTION
                           "Lost IPX packets due to memory limitations."
                   ::= { tmpnovell 19 }

               ipxActLostByts OBJECT-TYPE





          -- cisco MIB                                        [Page 105]
--





          -- Request for Comments: Draft             cisco Systems, Inc.


                   SYNTAX  INTEGER
                   ACCESS  read-only
                   STATUS  mandatory
                   DESCRIPTION
                           "Total bytes of lost IPX packets."
                   ::= { tmpnovell 20 }


               -- Local IPX Accounting Table

          -- This group provides access to the cisco IPX accounting
          -- support.

               lipxAccountingTable OBJECT-TYPE
                   SYNTAX  SEQUENCE OF LIpxAccountEntry
                   ACCESS  not-accessible
                   STATUS  mandatory
                   DESCRIPTION
                            "A list of IPX accounting entries."
                   ::= { tmpnovell 21 }

               lipxAccountingEntry OBJECT-TYPE
                   SYNTAX LIpxAccountEntry
                   ACCESS  not-accessible
                   STATUS  mandatory
                   DESCRIPTION
                           "IPX accounting entry"
                   INDEX { ipxActSrc, ipxActDst }
               ::= { lipxAccountingTable 1 }

               LIpxAccountEntry ::=
                   SEQUENCE {
                       ipxActSrc
                           OCTET STRING,
                       ipxActDst
                           OCTET STRING,
                       ipxActPkts
                           INTEGER,
                       ipxActByts
                           INTEGER
                   }


          -- The following section describes the components of the
          -- table.






          -- cisco MIB                                        [Page 106]
--





          -- Request for Comments: Draft             cisco Systems, Inc.


               ipxActSrc OBJECT-TYPE
                   SYNTAX  OCTET STRING
                   ACCESS  read-only
                   STATUS  mandatory
                   DESCRIPTION
                           "IPX Source address for host traffic matrix."
                   ::= { lipxAccountingEntry 1 }

               ipxActDst OBJECT-TYPE
                   SYNTAX  OCTET STRING
                   ACCESS  read-only
                   STATUS  mandatory
                   DESCRIPTION
                           "IPX Destination address for host traffic
                           matrix."
                   ::= { lipxAccountingEntry 2 }

               ipxActPkts OBJECT-TYPE
                   SYNTAX  INTEGER
                   ACCESS  read-only
                   STATUS  mandatory
                   DESCRIPTION
                           "Number of IPX packets sent from source to
                           destination."
                   ::= { lipxAccountingEntry 3 }

               ipxActByts OBJECT-TYPE
                   SYNTAX  INTEGER
                   ACCESS  read-only
                   STATUS  mandatory
                   DESCRIPTION
                           "Total number of bytes in IPX packets from
                           source to destination."
                   ::= { lipxAccountingEntry 4 }

               -- End of table


               ipxActAge OBJECT-TYPE
                   SYNTAX  TimeTicks
                   ACCESS  read-only
                   STATUS  mandatory
                   DESCRIPTION
                           "The age of the data in the current IPX data
                           matrix."





          -- cisco MIB                                        [Page 107]
--





          -- Request for Comments: Draft             cisco Systems, Inc.


                   ::= { tmpnovell 22 }


               -- Local IPX Checkpoint Accounting Table

          -- Local IPX Checkpoint Accounting Table

               lipxCkAccountingTable OBJECT-TYPE
                   SYNTAX  SEQUENCE OF LIpxCkAccountEntry
                   ACCESS  not-accessible
                   STATUS  mandatory
                   DESCRIPTION
                            "A list of IPX checkpoint accounting
                            entries."
                   ::= { tmpnovell 23 }

               lipxCkAccountingEntry OBJECT-TYPE
                   SYNTAX LIpxCkAccountEntry
                   ACCESS  not-accessible
                   STATUS  mandatory
                   DESCRIPTION
                           "IPX checkpoint accounting entry"
                   INDEX { ipxCkactSrc, ipxCkactDst }
               ::= { lipxCkAccountingTable 1 }

               LIpxCkAccountEntry ::=
                   SEQUENCE {
                       ipxCkactSrc
                           OCTET STRING,
                       ipxCkactDst
                           OCTET STRING,
                       ipxCkactPkts
                           INTEGER,
                       ipxCkactByts
                           Counter
                   }


          -- The following section describes the components of the
          -- table.

               ipxCkactSrc OBJECT-TYPE
                   SYNTAX  OCTET STRING
                   ACCESS  read-only
                   STATUS  mandatory
                   DESCRIPTION





          -- cisco MIB                                        [Page 108]
--





          -- Request for Comments: Draft             cisco Systems, Inc.


                           "IPX Source address for host in checkpoint
                           traffic matrix."
                   ::= { lipxCkAccountingEntry 1 }

               ipxCkactDst OBJECT-TYPE
                   SYNTAX  OCTET STRING
                   ACCESS  read-only
                   STATUS  mandatory
                   DESCRIPTION
                           "IPX Destination address for host in
                           checkpoint traffic matrix."
                   ::= { lipxCkAccountingEntry 2 }

               ipxCkactPkts OBJECT-TYPE
                   SYNTAX  INTEGER
                   ACCESS  read-only
                   STATUS  mandatory
                   DESCRIPTION
                           "Number of IPX packets sent from source to
                           destination in checkpoint matrix."
                   ::= { lipxCkAccountingEntry 3 }

               ipxCkactByts OBJECT-TYPE
                   SYNTAX  Counter
                   ACCESS  read-only
                   STATUS  mandatory
                   DESCRIPTION
                           "Total number of bytes in IPX packets from
                           source to destination in checkpoint matrix."
                   ::= { lipxCkAccountingEntry 4 }

               -- End of table


               ipxCkactAge OBJECT-TYPE
                   SYNTAX  TimeTicks
                   ACCESS  read-only
                   STATUS  mandatory
                   DESCRIPTION
                           "Age of data in the IPX checkpoint matrix."
                   ::= { tmpnovell 24 }

               ipxActCheckPoint OBJECT-TYPE
                   SYNTAX  INTEGER
                   ACCESS  read-write





          -- cisco MIB                                        [Page 109]
--





          -- Request for Comments: Draft             cisco Systems, Inc.


                   STATUS  mandatory
                   DESCRIPTION
                           "Check points the IPX accounting database.
                           This mib variable must be read and then set
                           with the same value for the check point to
                           succeed. The value read and then set will be
                           incremented aftera successful set request"
                   ::= { tmpnovell 25 }


               -- Temporary Vines Section

          -- This group is present in all router based products.

               vinesInput OBJECT-TYPE
                   SYNTAX  INTEGER
                   ACCESS  read-only
                   STATUS  mandatory
                   DESCRIPTION
                           "Total input count of number of Vines
                           packets."
                   ::= { tmpvines 1 }

               vinesOutput OBJECT-TYPE
                   SYNTAX  INTEGER
                   ACCESS  read-only
                   STATUS  mandatory
                   DESCRIPTION
                           "Total count of number of Vines output
                           packets."
                   ::= { tmpvines 2 }

               vinesLocaldest OBJECT-TYPE
                   SYNTAX  INTEGER
                   ACCESS  read-only
                   STATUS  mandatory
                   DESCRIPTION
                           "Total count of Vines input packets for this
                           host."
                   ::= { tmpvines 3 }

               vinesForwarded OBJECT-TYPE
                   SYNTAX  INTEGER
                   ACCESS  read-only
                   STATUS  mandatory





          -- cisco MIB                                        [Page 110]
--





          -- Request for Comments: Draft             cisco Systems, Inc.


                   DESCRIPTION
                           "Total count of number of Vines packets
                           forwarded."
                   ::= { tmpvines 4 }

               vinesBcastin OBJECT-TYPE
                   SYNTAX  INTEGER
                   ACCESS  read-only
                   STATUS  mandatory
                   DESCRIPTION
                           "Total count of number of Vines input
                           broadcast packets."
                   ::= { tmpvines 5 }

               vinesBcastout OBJECT-TYPE
                   SYNTAX  INTEGER
                   ACCESS  read-only
                   STATUS  mandatory
                   DESCRIPTION
                           "Total count of number of Vines output
                           broadcast packets."
                   ::= { tmpvines 6 }

               vinesBcastfwd OBJECT-TYPE
                   SYNTAX  INTEGER
                   ACCESS  read-only
                   STATUS  mandatory
                   DESCRIPTION
                           "Total count of number of Vines broadcast
                           packets forwarded."
                   ::= { tmpvines 7 }

               vinesNotlan OBJECT-TYPE
                   SYNTAX  INTEGER
                   ACCESS  read-only
                   STATUS  mandatory
                   DESCRIPTION
                           "Total count of number of Vines broadcast
                           packets not forwarded to all interfaces
                           because the LAN ONLY bit was set."
                   ::= { tmpvines 8 }

               vinesNotgt4800 OBJECT-TYPE
                   SYNTAX  INTEGER
                   ACCESS  read-only





          -- cisco MIB                                        [Page 111]
--





          -- Request for Comments: Draft             cisco Systems, Inc.


                   STATUS  mandatory
                   DESCRIPTION
                           "Total count of number of Vines broadcast
                           packets not forwarded to all interfaces
                           because the OVER 4800 BPS bit was set."
                   ::= { tmpvines 9 }

               vinesNocharges OBJECT-TYPE
                   SYNTAX  INTEGER
                   ACCESS  read-only
                   STATUS  mandatory
                   DESCRIPTION
                           "Total count of number of Vines broadcast
                           packets not forwarded to all interfaces
                           because the NO CHARGES only bit was set."
                   ::= { tmpvines 10 }

               vinesFormaterror OBJECT-TYPE
                   SYNTAX  INTEGER
                   ACCESS  read-only
                   STATUS  mandatory
                   DESCRIPTION
                           "Total count of number of Vines input packets
                           with header errors."
                   ::= { tmpvines 11 }

               vinesCksumerr OBJECT-TYPE
                   SYNTAX  INTEGER
                   ACCESS  read-only
                   STATUS  mandatory
                   DESCRIPTION
                           "Total count of number of Vines input packets
                           with checksum erors."
                   ::= { tmpvines 12 }

               vinesHopcount OBJECT-TYPE
                   SYNTAX  INTEGER
                   ACCESS  read-only
                   STATUS  mandatory
                   DESCRIPTION
                           "Total count of number of Vines input packets
                           that have exceeded the maximum hop count."
                   ::= { tmpvines 13 }

               vinesNoroute OBJECT-TYPE





          -- cisco MIB                                        [Page 112]
--





          -- Request for Comments: Draft             cisco Systems, Inc.


                   SYNTAX  INTEGER
                   ACCESS  read-only
                   STATUS  mandatory
                   DESCRIPTION
                           "Total count of number of Vines packets
                           dropped due to no route."
                   ::= { tmpvines 14 }

               vinesEncapsfailed OBJECT-TYPE
                   SYNTAX  INTEGER
                   ACCESS  read-only
                   STATUS  mandatory
                   DESCRIPTION
                           "Total count of number of Vines packets
                           dropped due to output encapsulation failed."
                   ::= { tmpvines 15 }

               vinesUnknown OBJECT-TYPE
                   SYNTAX  INTEGER
                   ACCESS  read-only
                   STATUS  mandatory
                   DESCRIPTION
                           "Total count of number of unknown Vines input
                           packets."
                   ::= { tmpvines 16 }

               vinesIcpIn OBJECT-TYPE
                   SYNTAX  INTEGER
                   ACCESS  read-only
                   STATUS  mandatory
                   DESCRIPTION
                           "Total count of number of Vines ICP packets
                           received."
                   ::= { tmpvines 17 }

               vinesIcpOut OBJECT-TYPE
                   SYNTAX  INTEGER
                   ACCESS  read-only
                   STATUS  mandatory
                   DESCRIPTION
                           "Total count of number of Vines ICP packets
                           generaed."
                   ::= { tmpvines 18 }

               vinesMetricOut OBJECT-TYPE





          -- cisco MIB                                        [Page 113]
--





          -- Request for Comments: Draft             cisco Systems, Inc.


                   SYNTAX  INTEGER
                   ACCESS  read-only
                   STATUS  mandatory
                   DESCRIPTION
                           "Total count of number of Vines ICP Metric
                           Notification packets generated."
                   ::= { tmpvines 19 }

               vinesMacEchoIn OBJECT-TYPE
                   SYNTAX  INTEGER
                   ACCESS  read-only
                   STATUS  mandatory
                   DESCRIPTION
                           "Total count of number of Vines MAC level
                           Echo packets received."
                   ::= { tmpvines 20 }

               vinesMacEchoOut OBJECT-TYPE
                   SYNTAX  INTEGER
                   ACCESS  read-only
                   STATUS  mandatory
                   DESCRIPTION
                           "Total count of number of Vines MAC level
                           Echo packets generated."
                   ::= { tmpvines 21 }

               vinesEchoIn OBJECT-TYPE
                   SYNTAX  INTEGER
                   ACCESS  read-only
                   STATUS  mandatory
                   DESCRIPTION
                           "Total count of number of Vines Echo packets
                           received."
                   ::= { tmpvines 22 }

               vinesEchoOut OBJECT-TYPE
                   SYNTAX  INTEGER
                   ACCESS  read-only
                   STATUS  mandatory
                   DESCRIPTION
                           "Total count of number of Vines Echo packets
                           generated."
                   ::= { tmpvines 23 }

               vinesProxyCnt OBJECT-TYPE





          -- cisco MIB                                        [Page 114]
--





          -- Request for Comments: Draft             cisco Systems, Inc.


                   SYNTAX  Counter
                   ACCESS  read-only
                   STATUS  mandatory
                   DESCRIPTION
                           "Total count of proxy packets sent."
                   ::= { tmpvines 24 }

               vinesProxyReplyCnt OBJECT-TYPE
                   SYNTAX  Counter
                   ACCESS  read-only
                   STATUS  mandatory
                   DESCRIPTION
                           "Total count of responses to proxy packets."
                   ::= { tmpvines 25 }

               vinesNet OBJECT-TYPE
                   SYNTAX  INTEGER
                   ACCESS  read-only
                   STATUS  mandatory
                   DESCRIPTION
                           "Vines network number of this router."
                   ::= { tmpvines 26 }

               vinesSubNet OBJECT-TYPE
                   SYNTAX  INTEGER
                   ACCESS  read-only
                   STATUS  mandatory
                   DESCRIPTION
                           "Vines sub-network number of this router."
                   ::= { tmpvines 27 }

               vinesClient OBJECT-TYPE
                   SYNTAX  INTEGER
                   ACCESS  read-only
                   STATUS  mandatory
                   DESCRIPTION
                           "Next Vines client sub-network number to be
                           assigned by this router."
                   ::= { tmpvines 28 }

               tmpvinesIfTable OBJECT-TYPE
                   SYNTAX  SEQUENCE OF VinesIfTableEntry
                   ACCESS  not-accessible
                   STATUS  mandatory
                   DESCRIPTION





          -- cisco MIB                                        [Page 115]
--





          -- Request for Comments: Draft             cisco Systems, Inc.


                            "Vines interface table"
                   ::= { tmpvines 29 }

               tmpvinesIfTableEntry OBJECT-TYPE
                   SYNTAX VinesIfTableEntry
                   ACCESS  not-accessible
                   STATUS  mandatory
                   DESCRIPTION
                            "VINES interface table"
                   INDEX { ifIndex }
               ::= { tmpvinesIfTable 1 }

               VinesIfTableEntry ::=
                   SEQUENCE {
                       vinesIfMetric
                           INTEGER,
                       vinesIfEnctype
                           INTEGER,
                       vinesIfAccesslist
                           INTEGER,
                       vinesIfPropagate
                           INTEGER,
                       vinesIfArpEnabled
                           INTEGER,
                       vinesIfServerless
                           INTEGER,
                       vinesIfServerlessBcast
                           INTEGER,
                       vinesIfRedirectInterval
                           INTEGER,
                       vinesIfSplitDisabled
                           INTEGER,
                       vinesIfLineup
                           INTEGER,
                       vinesIfFastokay
                           INTEGER,
                       vinesIfRouteCache
                           INTEGER,
                       vinesIfIns
                           Counter,
                       vinesIfOuts
                           Counter,
                       vinesIfInBytes
                           Counter,
                       vinesIfOutBytes





          -- cisco MIB                                        [Page 116]
--





          -- Request for Comments: Draft             cisco Systems, Inc.


                           Counter,
                       vinesIfRxNotEnabledCnt
                           Counter,
                       vinesIfRxFormatErrorCnt
                           Counter,
                       vinesIfRxLocalDestCnt
                           Counter,
                       vinesIfRxBcastinCnt
                           Counter,
                       vinesIfRxForwardedCnt
                           Counter,
                       vinesIfRxNoRouteCnt
                           Counter,
                       vinesIfRxZeroHopCountCnt
                           Counter,
                       vinesIfRxChecksumErrorCnt
                           Counter,
                       vinesIfRxArp0Cnt
                           Counter,
                       vinesIfRxArp1Cnt
                           Counter,
                       vinesIfRxArp2Cnt
                           Counter,
                       vinesIfRxArp3Cnt
                           Counter,
                       vinesIfRxArpIllegalCnt
                           Counter,
                       vinesIfRxIcpErrorCnt
                           Counter,
                       vinesIfRxIcpMetricCnt
                           Counter,
                       vinesIfRxIcpIllegalCnt
                           Counter,
                       vinesIfRxIpcCnt
                           Counter,
                       vinesIfRxRtp0Cnt
                           Counter,
                       vinesIfRxRtp1Cnt
                           Counter,
                       vinesIfRxRtp2Cnt
                           Counter,
                       vinesIfRxRtp3Cnt
                           Counter,
                       vinesIfRxRtp4Cnt
                           Counter,





          -- cisco MIB                                        [Page 117]
--





          -- Request for Comments: Draft             cisco Systems, Inc.


                       vinesIfRxRtp5Cnt
                           Counter,
                       vinesIfRxRtp6Cnt
                           Counter,
                       vinesIfRxRtpIllegalCnt
                           Counter,
                       vinesIfRxSppCnt
                           Counter,
                       vinesIfRxIpUnknownCnt
                           Counter,
                       vinesIfRxIpcUnknownCnt
                           Counter,
                       vinesIfRxBcastHelperedCnt
                           Counter,
                       vinesIfRxBcastForwardedCnt
                           Counter,
                       vinesIfRxBcastDuplicateCnt
                           Counter,
                       vinesIfRxEchoCnt
                           Counter,
                       vinesIfRxMacEchoCnt
                           Counter,
                       vinesIfRxProxyReplyCnt
                           Counter,
                       vinesIfTxUnicastCnt
                           Counter,
                       vinesIfTxBcastCnt
                           Counter,
                       vinesIfTxForwardedCnt
                           Counter,
                       vinesIfTxFailedEncapsCnt
                           Counter,
                       vinesIfTxFailedAccessCnt
                           Counter,
                       vinesIfTxFailedDownCnt
                           Counter,
                       vinesIfTxNotBcastToSourceCnt
                           Counter,
                       vinesIfTxNotBcastNotlanCnt
                           Counter,
                       vinesIfTxNotBcastNotgt4800Cnt
                           Counter,
                       vinesIfTxNotBcastPpchargeCnt
                           Counter,
                       vinesIfTxBcastForwardedCnt





          -- cisco MIB                                        [Page 118]
--





          -- Request for Comments: Draft             cisco Systems, Inc.


                           Counter,
                       vinesIfTxBcastHelperedCnt
                           Counter,
                       vinesIfTxArp0Cnt
                           Counter,
                       vinesIfTxArp1Cnt
                           Counter,
                       vinesIfTxArp2Cnt
                           Counter,
                       vinesIfTxArp3Cnt
                           Counter,
                       vinesIfTxIcpErrorCnt
                           Counter,
                       vinesIfTxIcpMetricCnt
                           Counter,
                       vinesIfTxIpcCnt
                           Counter,
                       vinesIfTxRtp0Cnt
                           Counter,
                       vinesIfTxRtp1Cnt
                           Counter,
                       vinesIfTxRtp2Cnt
                           Counter,
                       vinesIfTxRtp3Cnt
                           Counter,
                       vinesIfTxRtp4Cnt
                           Counter,
                       vinesIfTxRtp5Cnt
                           Counter,
                       vinesIfTxRtp6Cnt
                           Counter,
                       vinesIfTxSppCnt
                           Counter,
                       vinesIfTxEchoCnt
                           Counter,
                       vinesIfTxMacEchoCnt
                           Counter,
                       vinesIfTxProxyCnt
                           Counter,
                       vinesIfInputRouterFilter
                           INTEGER,
                       vinesIfInputNetworkFilter
                           INTEGER,
                       vinesIfOutputNetworkFilter
                           INTEGER
                   }


          -- The following section describes the components of the
          -- table.






          -- cisco MIB                                        [Page 119]
--





          -- Request for Comments: Draft             cisco Systems, Inc.


               vinesIfMetric OBJECT-TYPE
                   SYNTAX  INTEGER
                   ACCESS  read-only
                   STATUS  mandatory
                   DESCRIPTION
                           "Vines protocol metric value."
                   ::= { tmpvinesIfTableEntry 1 }

               vinesIfEnctype OBJECT-TYPE
                   SYNTAX  INTEGER
                   ACCESS  read-only
                   STATUS  mandatory
                   DESCRIPTION
                           "Vines protocol default encapsulation"
                   ::= { tmpvinesIfTableEntry 2 }

               vinesIfAccesslist OBJECT-TYPE
                   SYNTAX  INTEGER
                   ACCESS  read-only
                   STATUS  mandatory
                   DESCRIPTION
                           "Vines protocol outgoing access list number."
                   ::= { tmpvinesIfTableEntry 3 }

               vinesIfPropagate OBJECT-TYPE
                   SYNTAX  INTEGER
                   ACCESS  read-only
                   STATUS  mandatory
                   DESCRIPTION
                           "Vines protocol 'propagate' enabled."
                   ::= { tmpvinesIfTableEntry 4 }

               vinesIfArpEnabled OBJECT-TYPE
                   SYNTAX  INTEGER
                   ACCESS  read-only
                   STATUS  mandatory
                   DESCRIPTION
                           "Vines protocol arp replies enabled."
                   ::= { tmpvinesIfTableEntry 5 }

               vinesIfServerless OBJECT-TYPE
                   SYNTAX  INTEGER
                   ACCESS  read-only
                   STATUS  mandatory
                   DESCRIPTION





          -- cisco MIB                                        [Page 120]
--





          -- Request for Comments: Draft             cisco Systems, Inc.


                           "Vines protocol serverless support enabled."
                   ::= { tmpvinesIfTableEntry 6 }

               vinesIfServerlessBcast OBJECT-TYPE
                   SYNTAX  INTEGER
                   ACCESS  read-only
                   STATUS  mandatory
                   DESCRIPTION
                           "Vines protocol serverless broadcasting
                           support enabled."
                   ::= { tmpvinesIfTableEntry 7 }

               vinesIfRedirectInterval OBJECT-TYPE
                   SYNTAX  INTEGER
                   ACCESS  read-only
                   STATUS  mandatory
                   DESCRIPTION
                           "Vines protocol redirect interval (in ms)."
                   ::= { tmpvinesIfTableEntry 8 }

               vinesIfSplitDisabled OBJECT-TYPE
                   SYNTAX  INTEGER
                   ACCESS  read-only
                   STATUS  mandatory
                   DESCRIPTION
                           "Vines protocol split horizon disabled"
                   ::= { tmpvinesIfTableEntry 9 }

               vinesIfLineup OBJECT-TYPE
                   SYNTAX  INTEGER
                   ACCESS  read-only
                   STATUS  mandatory
                   DESCRIPTION
                           "Vines protocol line up/down."
                   ::= { tmpvinesIfTableEntry 10 }

               vinesIfFastokay OBJECT-TYPE
                   SYNTAX  INTEGER
                   ACCESS  read-only
                   STATUS  mandatory
                   DESCRIPTION
                           "Vines protocol fast switching supported."
                   ::= { tmpvinesIfTableEntry 11 }

               vinesIfRouteCache OBJECT-TYPE





          -- cisco MIB                                        [Page 121]
--





          -- Request for Comments: Draft             cisco Systems, Inc.


                   SYNTAX  INTEGER
                   ACCESS  read-only
                   STATUS  mandatory
                   DESCRIPTION
                           "Vines protocol fast switching requested"
                   ::= { tmpvinesIfTableEntry 12 }

               vinesIfIns OBJECT-TYPE
                   SYNTAX  Counter
                   ACCESS  read-only
                   STATUS  mandatory
                   DESCRIPTION
                           "Vines protocol input packet count"
                   ::= { tmpvinesIfTableEntry 13 }

               vinesIfOuts OBJECT-TYPE
                   SYNTAX  Counter
                   ACCESS  read-only
                   STATUS  mandatory
                   DESCRIPTION
                           "Vines protocol output packet count"
                   ::= { tmpvinesIfTableEntry 14 }

               vinesIfInBytes OBJECT-TYPE
                   SYNTAX  Counter
                   ACCESS  read-only
                   STATUS  mandatory
                   DESCRIPTION
                           "Vines protocol input octet count"
                   ::= { tmpvinesIfTableEntry 15 }

               vinesIfOutBytes OBJECT-TYPE
                   SYNTAX  Counter
                   ACCESS  read-only
                   STATUS  mandatory
                   DESCRIPTION
                           "Vines protocol output octet count"
                   ::= { tmpvinesIfTableEntry 16 }

               vinesIfRxNotEnabledCnt OBJECT-TYPE
                   SYNTAX  Counter
                   ACCESS  read-only
                   STATUS  mandatory
                   DESCRIPTION
                           "Vines protocol count of input packets





          -- cisco MIB                                        [Page 122]
--





          -- Request for Comments: Draft             cisco Systems, Inc.


                           discarded because interface not configured."
                   ::= { tmpvinesIfTableEntry 17 }

               vinesIfRxFormatErrorCnt OBJECT-TYPE
                   SYNTAX  Counter
                   ACCESS  read-only
                   STATUS  mandatory
                   DESCRIPTION
                           "Vines protocol count of input packets with
                           format errors."
                   ::= { tmpvinesIfTableEntry 18 }

               vinesIfRxLocalDestCnt OBJECT-TYPE
                   SYNTAX  Counter
                   ACCESS  read-only
                   STATUS  mandatory
                   DESCRIPTION
                           "Vines protocol count of input packets
                           destined for this router."
                   ::= { tmpvinesIfTableEntry 19 }

               vinesIfRxBcastinCnt OBJECT-TYPE
                   SYNTAX  Counter
                   ACCESS  read-only
                   STATUS  mandatory
                   DESCRIPTION
                           "Vines protocol input broadcast count."
                   ::= { tmpvinesIfTableEntry 20 }

               vinesIfRxForwardedCnt OBJECT-TYPE
                   SYNTAX  Counter
                   ACCESS  read-only
                   STATUS  mandatory
                   DESCRIPTION
                           "Vines protocol count of input packets
                           forwarded to another interface."
                   ::= { tmpvinesIfTableEntry 21 }

               vinesIfRxNoRouteCnt OBJECT-TYPE
                   SYNTAX  Counter
                   ACCESS  read-only
                   STATUS  mandatory
                   DESCRIPTION
                           "Vines protocol count of input packets
                           dropped because there was no route to the





          -- cisco MIB                                        [Page 123]
--





          -- Request for Comments: Draft             cisco Systems, Inc.


                           destination."
                   ::= { tmpvinesIfTableEntry 22 }

               vinesIfRxZeroHopCountCnt OBJECT-TYPE
                   SYNTAX  Counter
                   ACCESS  read-only
                   STATUS  mandatory
                   DESCRIPTION
                           "Vines protocol count of input packets
                           dropped due to a zero hop count."
                   ::= { tmpvinesIfTableEntry 23 }

               vinesIfRxChecksumErrorCnt OBJECT-TYPE
                   SYNTAX  Counter
                   ACCESS  read-only
                   STATUS  mandatory
                   DESCRIPTION
                           "Vines protocol count of input packets with
                           checksum errors."
                   ::= { tmpvinesIfTableEntry 24 }

               vinesIfRxArp0Cnt OBJECT-TYPE
                   SYNTAX  Counter
                   ACCESS  read-only
                   STATUS  mandatory
                   DESCRIPTION
                           "Vines protocol count of input ARP Query
                           Request messages."
                   ::= { tmpvinesIfTableEntry 25 }

               vinesIfRxArp1Cnt OBJECT-TYPE
                   SYNTAX  Counter
                   ACCESS  read-only
                   STATUS  mandatory
                   DESCRIPTION
                           "Vines protocol count of input ARP Query
                           Response messages."
                   ::= { tmpvinesIfTableEntry 26 }

               vinesIfRxArp2Cnt OBJECT-TYPE
                   SYNTAX  Counter
                   ACCESS  read-only
                   STATUS  mandatory
                   DESCRIPTION
                           "Vines protocol count of input ARP Assignment





          -- cisco MIB                                        [Page 124]
--





          -- Request for Comments: Draft             cisco Systems, Inc.


                           Request messages."
                   ::= { tmpvinesIfTableEntry 27 }

               vinesIfRxArp3Cnt OBJECT-TYPE
                   SYNTAX  Counter
                   ACCESS  read-only
                   STATUS  mandatory
                   DESCRIPTION
                           "Vines protocol count of input ARP Assignment
                           Response messages."
                   ::= { tmpvinesIfTableEntry 28 }

               vinesIfRxArpIllegalCnt OBJECT-TYPE
                   SYNTAX  Counter
                   ACCESS  read-only
                   STATUS  mandatory
                   DESCRIPTION
                           "Vines protocol count of input illegal ARP
                           messages."
                   ::= { tmpvinesIfTableEntry 29 }

               vinesIfRxIcpErrorCnt OBJECT-TYPE
                   SYNTAX  Counter
                   ACCESS  read-only
                   STATUS  mandatory
                   DESCRIPTION
                           "Vines protocol count of input ICP error
                           messages."
                   ::= { tmpvinesIfTableEntry 30 }

               vinesIfRxIcpMetricCnt OBJECT-TYPE
                   SYNTAX  Counter
                   ACCESS  read-only
                   STATUS  mandatory
                   DESCRIPTION
                           "Vines protocol count of input ICP metric
                           messages."
                   ::= { tmpvinesIfTableEntry 31 }

               vinesIfRxIcpIllegalCnt OBJECT-TYPE
                   SYNTAX  Counter
                   ACCESS  read-only
                   STATUS  mandatory
                   DESCRIPTION
                           "Vines protocol count of input illegal ICP





          -- cisco MIB                                        [Page 125]
--





          -- Request for Comments: Draft             cisco Systems, Inc.


                           messages."
                   ::= { tmpvinesIfTableEntry 32 }

               vinesIfRxIpcCnt OBJECT-TYPE
                   SYNTAX  Counter
                   ACCESS  read-only
                   STATUS  mandatory
                   DESCRIPTION
                           "Vines protocol count of input IPC messages."
                   ::= { tmpvinesIfTableEntry 33 }

               vinesIfRxRtp0Cnt OBJECT-TYPE
                   SYNTAX  Counter
                   ACCESS  read-only
                   STATUS  mandatory
                   DESCRIPTION
                           "Vines protocol count of input RTP type 0
                           messages."
                   ::= { tmpvinesIfTableEntry 34 }

               vinesIfRxRtp1Cnt OBJECT-TYPE
                   SYNTAX  Counter
                   ACCESS  read-only
                   STATUS  mandatory
                   DESCRIPTION
                           "Vines protocol count of input RTP Request
                           messages."
                   ::= { tmpvinesIfTableEntry 35 }

               vinesIfRxRtp2Cnt OBJECT-TYPE
                   SYNTAX  Counter
                   ACCESS  read-only
                   STATUS  mandatory
                   DESCRIPTION
                           "Vines protocol count of input RTP type 2
                           messages."
                   ::= { tmpvinesIfTableEntry 36 }

               vinesIfRxRtp3Cnt OBJECT-TYPE
                   SYNTAX  Counter
                   ACCESS  read-only
                   STATUS  mandatory
                   DESCRIPTION
                           "Vines protocol count of input RTP type 3
                           messages."





          -- cisco MIB                                        [Page 126]
--





          -- Request for Comments: Draft             cisco Systems, Inc.


                   ::= { tmpvinesIfTableEntry 37 }

               vinesIfRxRtp4Cnt OBJECT-TYPE
                   SYNTAX  Counter
                   ACCESS  read-only
                   STATUS  mandatory
                   DESCRIPTION
                           "Vines protocol count of input RTP Update
                           messages."
                   ::= { tmpvinesIfTableEntry 38 }

               vinesIfRxRtp5Cnt OBJECT-TYPE
                   SYNTAX  Counter
                   ACCESS  read-only
                   STATUS  mandatory
                   DESCRIPTION
                           "Vines protocol count of input RTP Response
                           messages."
                   ::= { tmpvinesIfTableEntry 39 }

               vinesIfRxRtp6Cnt OBJECT-TYPE
                   SYNTAX  Counter
                   ACCESS  read-only
                   STATUS  mandatory
                   DESCRIPTION
                           "Vines protocol count of input RTP Redirect
                           messages."
                   ::= { tmpvinesIfTableEntry 40 }

               vinesIfRxRtpIllegalCnt OBJECT-TYPE
                   SYNTAX  Counter
                   ACCESS  read-only
                   STATUS  mandatory
                   DESCRIPTION
                           "Vines protocol count of input illegal RTP
                           messages."
                   ::= { tmpvinesIfTableEntry 41 }

               vinesIfRxSppCnt OBJECT-TYPE
                   SYNTAX  Counter
                   ACCESS  read-only
                   STATUS  mandatory
                   DESCRIPTION
                           "Vines protocol count of input SPP messages."
                   ::= { tmpvinesIfTableEntry 42 }





          -- cisco MIB                                        [Page 127]
--





          -- Request for Comments: Draft             cisco Systems, Inc.


               vinesIfRxIpUnknownCnt OBJECT-TYPE
                   SYNTAX  Counter
                   ACCESS  read-only
                   STATUS  mandatory
                   DESCRIPTION
                           "Vines protocol count of input packets of
                           unknown Vines protocols."
                   ::= { tmpvinesIfTableEntry 43 }

               vinesIfRxIpcUnknownCnt OBJECT-TYPE
                   SYNTAX  Counter
                   ACCESS  read-only
                   STATUS  mandatory
                   DESCRIPTION
                           "Vines protocol count of input packets of
                           unknown Vines IPC ports."
                   ::= { tmpvinesIfTableEntry 44 }

               vinesIfRxBcastHelperedCnt OBJECT-TYPE
                   SYNTAX  Counter
                   ACCESS  read-only
                   STATUS  mandatory
                   DESCRIPTION
                           "Vines protocol count of input packets
                           helpered to another server."
                   ::= { tmpvinesIfTableEntry 45 }

               vinesIfRxBcastForwardedCnt OBJECT-TYPE
                   SYNTAX  Counter
                   ACCESS  read-only
                   STATUS  mandatory
                   DESCRIPTION
                           "Vines protocol input broadcast forwarded to
                           other interface(s)."
                   ::= { tmpvinesIfTableEntry 46 }

               vinesIfRxBcastDuplicateCnt OBJECT-TYPE
                   SYNTAX  Counter
                   ACCESS  read-only
                   STATUS  mandatory
                   DESCRIPTION
                           "Vines protocol input duplicate broadcast
                           count."
                   ::= { tmpvinesIfTableEntry 47 }






          -- cisco MIB                                        [Page 128]
--





          -- Request for Comments: Draft             cisco Systems, Inc.


               vinesIfRxEchoCnt OBJECT-TYPE
                   SYNTAX  Counter
                   ACCESS  read-only
                   STATUS  mandatory
                   DESCRIPTION
                           "Vines protocol count of input IPC echo
                           messages."
                   ::= { tmpvinesIfTableEntry 48 }

               vinesIfRxMacEchoCnt OBJECT-TYPE
                   SYNTAX  Counter
                   ACCESS  read-only
                   STATUS  mandatory
                   DESCRIPTION
                           "Vines protocol count of input MAC layer echo
                           frames."
                   ::= { tmpvinesIfTableEntry 49 }

               vinesIfRxProxyReplyCnt OBJECT-TYPE
                   SYNTAX  Counter
                   ACCESS  read-only
                   STATUS  mandatory
                   DESCRIPTION
                           "Vines protocol count of responses to proxy
                           packets."
                   ::= { tmpvinesIfTableEntry 50 }

               vinesIfTxUnicastCnt OBJECT-TYPE
                   SYNTAX  Counter
                   ACCESS  read-only
                   STATUS  mandatory
                   DESCRIPTION
                           "Vines protocol unicast packets generated."
                   ::= { tmpvinesIfTableEntry 51 }

               vinesIfTxBcastCnt OBJECT-TYPE
                   SYNTAX  Counter
                   ACCESS  read-only
                   STATUS  mandatory
                   DESCRIPTION
                           "Vines protocol broadcastcast packets
                           generated."
                   ::= { tmpvinesIfTableEntry 52 }

               vinesIfTxForwardedCnt OBJECT-TYPE





          -- cisco MIB                                        [Page 129]
--





          -- Request for Comments: Draft             cisco Systems, Inc.


                   SYNTAX  Counter
                   ACCESS  read-only
                   STATUS  mandatory
                   DESCRIPTION
                           "Vines protocol count of forwarded packets."
                   ::= { tmpvinesIfTableEntry 53 }

               vinesIfTxFailedEncapsCnt OBJECT-TYPE
                   SYNTAX  Counter
                   ACCESS  read-only
                   STATUS  mandatory
                   DESCRIPTION
                           "Vines protocol output encapsulation
                           failures."
                   ::= { tmpvinesIfTableEntry 54 }

               vinesIfTxFailedAccessCnt OBJECT-TYPE
                   SYNTAX  Counter
                   ACCESS  read-only
                   STATUS  mandatory
                   DESCRIPTION
                           "Vines protocol output access list failures."
                   ::= { tmpvinesIfTableEntry 55 }

               vinesIfTxFailedDownCnt OBJECT-TYPE
                   SYNTAX  Counter
                   ACCESS  read-only
                   STATUS  mandatory
                   DESCRIPTION
                           "Vines protocol output interface down count."
                   ::= { tmpvinesIfTableEntry 56 }

               vinesIfTxNotBcastToSourceCnt OBJECT-TYPE
                   SYNTAX  Counter
                   ACCESS  read-only
                   STATUS  mandatory
                   DESCRIPTION
                           "Vines protocol output broadcast not sent
                           because interfaceleads back to the source."
                   ::= { tmpvinesIfTableEntry 57 }

               vinesIfTxNotBcastNotlanCnt OBJECT-TYPE
                   SYNTAX  Counter
                   ACCESS  read-only
                   STATUS  mandatory





          -- cisco MIB                                        [Page 130]
--





          -- Request for Comments: Draft             cisco Systems, Inc.


                   DESCRIPTION
                           "Vines protocol output broadcast not sent due
                           to 'Lan Only' class."
                   ::= { tmpvinesIfTableEntry 58 }

               vinesIfTxNotBcastNotgt4800Cnt OBJECT-TYPE
                   SYNTAX  Counter
                   ACCESS  read-only
                   STATUS  mandatory
                   DESCRIPTION
                           "Vines protocol output broadcast not sent due
                           to 'High Speed' class."
                   ::= { tmpvinesIfTableEntry 59 }

               vinesIfTxNotBcastPpchargeCnt OBJECT-TYPE
                   SYNTAX  Counter
                   ACCESS  read-only
                   STATUS  mandatory
                   DESCRIPTION
                           "Vines protocol output broadcast not sent due
                           to 'No Charges' class."
                   ::= { tmpvinesIfTableEntry 60 }

               vinesIfTxBcastForwardedCnt OBJECT-TYPE
                   SYNTAX  Counter
                   ACCESS  read-only
                   STATUS  mandatory
                   DESCRIPTION
                           "Vines protocol output broadcast forwarded
                           from another interface."
                   ::= { tmpvinesIfTableEntry 61 }

               vinesIfTxBcastHelperedCnt OBJECT-TYPE
                   SYNTAX  Counter
                   ACCESS  read-only
                   STATUS  mandatory
                   DESCRIPTION
                           "Vines protocol output broadcast helpered to
                           a vines server."
                   ::= { tmpvinesIfTableEntry 62 }

               vinesIfTxArp0Cnt OBJECT-TYPE
                   SYNTAX  Counter
                   ACCESS  read-only
                   STATUS  mandatory





          -- cisco MIB                                        [Page 131]
--





          -- Request for Comments: Draft             cisco Systems, Inc.


                   DESCRIPTION
                           "Vines protocol count of output ARP Query
                           Request messages."
                   ::= { tmpvinesIfTableEntry 63 }

               vinesIfTxArp1Cnt OBJECT-TYPE
                   SYNTAX  Counter
                   ACCESS  read-only
                   STATUS  mandatory
                   DESCRIPTION
                           "Vines protocol count of output ARP Query
                           Response messages."
                   ::= { tmpvinesIfTableEntry 64 }

               vinesIfTxArp2Cnt OBJECT-TYPE
                   SYNTAX  Counter
                   ACCESS  read-only
                   STATUS  mandatory
                   DESCRIPTION
                           "Vines protocol count of output ARP
                           Assignment Request messages."
                   ::= { tmpvinesIfTableEntry 65 }

               vinesIfTxArp3Cnt OBJECT-TYPE
                   SYNTAX  Counter
                   ACCESS  read-only
                   STATUS  mandatory
                   DESCRIPTION
                           "Vines protocol count of input ARP Assignment
                           Response messages."
                   ::= { tmpvinesIfTableEntry 66 }

               vinesIfTxIcpErrorCnt OBJECT-TYPE
                   SYNTAX  Counter
                   ACCESS  read-only
                   STATUS  mandatory
                   DESCRIPTION
                           "Vines protocol count of output IPC Error
                           messages."
                   ::= { tmpvinesIfTableEntry 67 }

               vinesIfTxIcpMetricCnt OBJECT-TYPE
                   SYNTAX  Counter
                   ACCESS  read-only
                   STATUS  mandatory





          -- cisco MIB                                        [Page 132]
--





          -- Request for Comments: Draft             cisco Systems, Inc.


                   DESCRIPTION
                           "Vines protocol count of output IPC metric
                           messages."
                   ::= { tmpvinesIfTableEntry 68 }

               vinesIfTxIpcCnt OBJECT-TYPE
                   SYNTAX  Counter
                   ACCESS  read-only
                   STATUS  mandatory
                   DESCRIPTION
                           "Vines protocol count of output ICP
                           messages."
                   ::= { tmpvinesIfTableEntry 69 }

               vinesIfTxRtp0Cnt OBJECT-TYPE
                   SYNTAX  Counter
                   ACCESS  read-only
                   STATUS  mandatory
                   DESCRIPTION
                           "Vines protocol count of output RTP type 0
                           messages."
                   ::= { tmpvinesIfTableEntry 70 }

               vinesIfTxRtp1Cnt OBJECT-TYPE
                   SYNTAX  Counter
                   ACCESS  read-only
                   STATUS  mandatory
                   DESCRIPTION
                           "Vines protocol count of output RTP Request
                           messages."
                   ::= { tmpvinesIfTableEntry 71 }

               vinesIfTxRtp2Cnt OBJECT-TYPE
                   SYNTAX  Counter
                   ACCESS  read-only
                   STATUS  mandatory
                   DESCRIPTION
                           "Vines protocol count of output RTP type 2
                           messages."
                   ::= { tmpvinesIfTableEntry 72 }

               vinesIfTxRtp3Cnt OBJECT-TYPE
                   SYNTAX  Counter
                   ACCESS  read-only
                   STATUS  mandatory





          -- cisco MIB                                        [Page 133]
--





          -- Request for Comments: Draft             cisco Systems, Inc.


                   DESCRIPTION
                           "Vines protocol count of output RTP type 3
                           messages."
                   ::= { tmpvinesIfTableEntry 73 }

               vinesIfTxRtp4Cnt OBJECT-TYPE
                   SYNTAX  Counter
                   ACCESS  read-only
                   STATUS  mandatory
                   DESCRIPTION
                           "Vines protocol count of output RTP Update
                           messages."
                   ::= { tmpvinesIfTableEntry 74 }

               vinesIfTxRtp5Cnt OBJECT-TYPE
                   SYNTAX  Counter
                   ACCESS  read-only
                   STATUS  mandatory
                   DESCRIPTION
                           "Vines protocol count of output RTP Response
                           messages."
                   ::= { tmpvinesIfTableEntry 75 }

               vinesIfTxRtp6Cnt OBJECT-TYPE
                   SYNTAX  Counter
                   ACCESS  read-only
                   STATUS  mandatory
                   DESCRIPTION
                           "Vines protocol count of output RTP Redirect
                           messages."
                   ::= { tmpvinesIfTableEntry 76 }

               vinesIfTxSppCnt OBJECT-TYPE
                   SYNTAX  Counter
                   ACCESS  read-only
                   STATUS  mandatory
                   DESCRIPTION
                           "Vines protocol count of output SPP
                           messages."
                   ::= { tmpvinesIfTableEntry 77 }

               vinesIfTxEchoCnt OBJECT-TYPE
                   SYNTAX  Counter
                   ACCESS  read-only
                   STATUS  mandatory





          -- cisco MIB                                        [Page 134]
--





          -- Request for Comments: Draft             cisco Systems, Inc.


                   DESCRIPTION
                           "Vines protocol count of output IPC echo
                           messages."
                   ::= { tmpvinesIfTableEntry 78 }

               vinesIfTxMacEchoCnt OBJECT-TYPE
                   SYNTAX  Counter
                   ACCESS  read-only
                   STATUS  mandatory
                   DESCRIPTION
                           "Vines protocol count of output IPCMAC layer
                           echo frames."
                   ::= { tmpvinesIfTableEntry 79 }

               vinesIfTxProxyCnt OBJECT-TYPE
                   SYNTAX  Counter
                   ACCESS  read-only
                   STATUS  mandatory
                   DESCRIPTION
                           "Vines protocol count of proxy packets sent."
                   ::= { tmpvinesIfTableEntry 80 }

               vinesIfInputRouterFilter OBJECT-TYPE
                   SYNTAX  INTEGER
                   ACCESS  read-only
                   STATUS  mandatory
                   DESCRIPTION
                           "Vines protocol filter on received routing
			   information source address."
                   ::= { tmpvinesIfTableEntry 81 }

               vinesIfInputNetworkFilter OBJECT-TYPE
                   SYNTAX  INTEGER
                   ACCESS  read-only
                   STATUS  mandatory
                   DESCRIPTION
                           "Vines protocol filter on received routing
			   information content."
                   ::= { tmpvinesIfTableEntry 82 }

               vinesIfOutputNetworkFilter OBJECT-TYPE
                   SYNTAX  INTEGER
                   ACCESS  read-only
                   STATUS  mandatory
                   DESCRIPTION
                           "Vines protocol filter on transmitted routing
			   information content."
                   ::= { tmpvinesIfTableEntry 83 }

               -- End of table



               -- Temporary Chassis Section


               -- (not the same as the IETF Chassis MIB)

          -- This group is present in all products.

               chassisType OBJECT-TYPE
                   SYNTAX  INTEGER {
                        unknown(1),
                        multibus(2),
                        agsplus(3),
                        igs(4),
                        c2000(5),
                        c3000(6),
                        c4000(7),
                        c7000(8),
                        cs-500(9),
                        c7010(10),
                        c2500(11),
                        c4500(12)
                   }





          -- cisco MIB                                        [Page 135]
--





          -- Request for Comments: Draft             cisco Systems, Inc.


                   ACCESS  read-only
                   STATUS  mandatory
                   DESCRIPTION
                           "Chassis type."
                   ::= { tmpchassis 1 }

               chassisVersion OBJECT-TYPE
                   SYNTAX  DisplayString
                   ACCESS  read-only
                   STATUS  mandatory
                   DESCRIPTION
                           "Chassis hardware revision level, or an empty
                           string if unavailable."
                   ::= { tmpchassis 2 }

               chassisId OBJECT-TYPE
                   SYNTAX  DisplayString
                   ACCESS  read-write
                   STATUS  mandatory
                   DESCRIPTION
                           "Unique ID string. Defaults to chassis serial
                           number if available, otherwise empty. Can
                           also be set with 'snmp-server chassis-id'."
                   ::= { tmpchassis 3 }

               romVersion OBJECT-TYPE
                   SYNTAX  DisplayString
                   ACCESS  read-only
                   STATUS  mandatory
                   DESCRIPTION
                           "ROM monitor version."
                   ::= { tmpchassis 4 }

               romSysVersion OBJECT-TYPE
                   SYNTAX  DisplayString
                   ACCESS  read-only
                   STATUS  mandatory
                   DESCRIPTION
                           "ROM system software version, or an empty
                           string if unavailable."
                   ::= { tmpchassis 5 }

               processorRam OBJECT-TYPE
                   SYNTAX  INTEGER
                   ACCESS  read-only





          -- cisco MIB                                        [Page 136]
--





          -- Request for Comments: Draft             cisco Systems, Inc.


                   STATUS  mandatory
                   DESCRIPTION
                           "Bytes of RAM available to CPU."
                   ::= { tmpchassis 6 }

               nvRAMSize OBJECT-TYPE
                   SYNTAX  INTEGER
                   ACCESS  read-only
                   STATUS  mandatory
                   DESCRIPTION
                           "Bytes of non-volatile configuration memory."
                   ::= { tmpchassis 7 }

               nvRAMUsed OBJECT-TYPE
                   SYNTAX  INTEGER
                   ACCESS  read-only
                   STATUS  mandatory
                   DESCRIPTION
                           "Bytes of non-volatile configuration memory
                           in use."
                   ::= { tmpchassis 8 }

               configRegister OBJECT-TYPE
                   SYNTAX  INTEGER
                   ACCESS  read-only
                   STATUS  mandatory
                   DESCRIPTION
                           "Value of configuration register."
                   ::= { tmpchassis 9 }

               configRegNext OBJECT-TYPE
                   SYNTAX  INTEGER
                   ACCESS  read-only
                   STATUS  mandatory
                   DESCRIPTION
                           "Value of configuration register at next
                           reload."
                   ::= { tmpchassis 10 }

               cardTable OBJECT-TYPE
                   SYNTAX  SEQUENCE OF CardTableEntry
                   ACCESS  not-accessible
                   STATUS  mandatory
                   DESCRIPTION
                            "Chassis card table."





          -- cisco MIB                                        [Page 137]
--





          -- Request for Comments: Draft             cisco Systems, Inc.


                   ::= { tmpchassis 11 }

               cardTableEntry OBJECT-TYPE
                   SYNTAX CardTableEntry
                   ACCESS  not-accessible
                   STATUS  mandatory
                   DESCRIPTION
                            "Chassis card table."
                   INDEX { cardIndex }
               ::= { cardTable 1 }

               CardTableEntry ::=
                   SEQUENCE {
                       cardIndex
                           INTEGER,
                       cardType
                           INTEGER,
                       cardDescr
                           DisplayString,
                       cardSerial
                           INTEGER,
                       cardHwVersion
                           DisplayString,
                       cardSwVersion
                           DisplayString,
                       cardSlotNumber
                           INTEGER
                   }


          -- The following section describes the components of the
          -- table.

               cardIndex OBJECT-TYPE
                   SYNTAX  INTEGER
                   ACCESS  read-only
                   STATUS  mandatory
                   DESCRIPTION
                           "Index into cardTable (not physical chassis
                           slot number)."
                   ::= { cardTableEntry 1 }

               cardType OBJECT-TYPE
                   SYNTAX  INTEGER {
                        unknown(1),





          -- cisco MIB                                        [Page 138]
--





          -- Request for Comments: Draft             cisco Systems, Inc.


                        csc1(2),
                        csc2(3),
                        csc3(4),
                        csc4(5),
                        rp(6),
                        csc-m(20),
                        csc-mt(21),
                        csc-mc(22),
                        csc-mcplus(23),
                        csc-envm(24),
                        csc-16(40),
                        csc-p(41),
                        csc-a(50),
                        csc-e1(51),
                        csc-e2(52),
                        csc-y(53),
                        csc-s(54),
                        csc-t(55),
                        sci4s(56),
                        sci2s2t(57),
                        sci4t(58),
                        mci1t(59),
                        mci2t(60),
                        mci1s(61),
                        mci1s1t(62),
                        mci2s(63),
                        mci1e(64),
                        mci1e1t(65),
                        mci1e2t(66),
                        mci1e1s(67),
                        mci1e1s1t(68),
                        mci1e2s(69),
                        mci2e(70),
                        mci2e1t(71),
                        mci2e2t(72),
                        mci2e1s(73),
                        mci2e1s1t(74),
                        mci2e2s(75),
                        csc-r(80),
                        csc-r16(81),
                        csc-r16m(82),
                        csc-1r(83),
                        csc-2r(84),
                        csc-cctl1(100),
                        csc-cctl2(101),





          -- cisco MIB                                        [Page 139]
--





          -- Request for Comments: Draft             cisco Systems, Inc.


                        csc-mec2(110),
                        csc-mec4(111),
                        csc-mec6(112),
                        csc-fci(113),
                        csc-fcit(114),
                        csc-hsci(115),
                        csc-ctr(116),
                        sp(150),
                        eip(151),
                        fip(152),
                        hip(153),
                        sip(154),
                        trip(155),
                        fsip(156),
                        aip(157),
                        mip(158),
                        ssp(159),
                        npm-4000-fddi-sas(200),
                        npm-4000-fddi-das(201),
                        npm-4000-1e(202),
                        npm-4000-1r(203),
                        npm-4000-2s(204),
                        npm-4000-2e1(205),
                        npm-4000-2e(206),
                        npm-4000-2r1(207),
                        npm-4000-2r(208),
                        npm-4000-4t(209)
                   }
                   ACCESS  read-only
                   STATUS  mandatory
                   DESCRIPTION
                           "Functional type of this card."
                   ::= { cardTableEntry 2 }

               cardDescr OBJECT-TYPE
                   SYNTAX  DisplayString
                   ACCESS  read-only
                   STATUS  mandatory
                   DESCRIPTION
                           "Text description of this card."
                   ::= { cardTableEntry 3 }

               cardSerial OBJECT-TYPE
                   SYNTAX  INTEGER
                   ACCESS  read-only
                   STATUS  mandatory
                   DESCRIPTION
                           "The serial number of this card, or zero if
                           unavailable."
                   ::= { cardTableEntry 4 }






          -- cisco MIB                                        [Page 140]
--





          -- Request for Comments: Draft             cisco Systems, Inc.


               cardHwVersion OBJECT-TYPE
                   SYNTAX  DisplayString
                   ACCESS  read-only
                   STATUS  mandatory
                   DESCRIPTION
                           "Hardware revision level of this card, or an
                           empty string if unavailable."
                   ::= { cardTableEntry 5 }

               cardSwVersion OBJECT-TYPE
                   SYNTAX  DisplayString
                   ACCESS  read-only
                   STATUS  mandatory
                   DESCRIPTION
                           "Version of the firmware or microcode
                           installed on this card, or an empty string if
                           unavailable."
                   ::= { cardTableEntry 6 }

               cardSlotNumber OBJECT-TYPE
                   SYNTAX  INTEGER
                   ACCESS  read-only
                   STATUS  mandatory
                   DESCRIPTION
                           "Chassis slot number, or -1 if neither
                           applicable nor determinable."
                   ::= { cardTableEntry 7 }

               -- End of table


               chassisSlots OBJECT-TYPE
                   SYNTAX  INTEGER
                   ACCESS  read-only
                   STATUS  mandatory
                   DESCRIPTION
                           "Number of slots in this chassis, or -1 of
                           neither applicable nor determinable."
                   ::= { tmpchassis 12 }
               END










          -- cisco MIB                                        [Page 141]
--
