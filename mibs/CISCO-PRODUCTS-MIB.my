-- *****************************************************************
-- CISCO-PRODUCTS-MIB.my:  Cisco Product Object Identifier Assignments
--
--
-- January 1995, Jeffrey T. Johnson
--
-- Copyright (c) 1995-2001, 2002, 2003, 2004 by cisco Systems, Inc.
-- All rights reserved.
-- 
-- *****************************************************************


CISCO-PRODUCTS-MIB DEFINITIONS ::= BEGIN

IMPORTS
	MODULE-IDENTITY
		FROM SNMPv2-SMI
	ciscoModules,
	ciscoProducts
		FROM CISCO-SMI;

ciscoProductsMIB MODULE-IDENTITY
	LAST-UPDATED	"200204051400Z"
	ORGANIZATION	"Cisco Systems, Inc."
	CONTACT-INFO
		"       Cisco Systems
			Customer Service

		Postal: 170 W Tasman Drive
			San Jose, CA  95134
			USA

		   Tel: +1 800 553-NETS

		E-mail: cs-snmp@cisco.com"
	DESCRIPTION
		"This module defines the object identifiers that are
		assigned to various hardware platforms, and hence are
		returned as values for sysObjectID"
        REVISION "200204051400Z"
        DESCRIPTION
                "CANA Assignments."
 	REVISION	"9505310000Z"
  	DESCRIPTION
		"Miscellaneous updates."
	::= { ciscoModules 2 }

-- older cisco routers (i.e. CGS, MGS, AGS) do not have the ability
-- to determine what kind of router they are.  these devices return
-- a sysObjectID value that indicates their configured functionality
ciscoGatewayServer OBJECT IDENTIFIER ::= { ciscoProducts 1 }
ciscoTerminalServer OBJECT IDENTIFIER ::= { ciscoProducts 2 }
ciscoTrouter OBJECT IDENTIFIER ::= { ciscoProducts 3 }
ciscoProtocolTranslator OBJECT IDENTIFIER ::= { ciscoProducts 4 }

-- newer devices return a sysObjectID value that corresponds to the
-- device model number
ciscoIGS OBJECT IDENTIFIER ::= { ciscoProducts 5 }
cisco3000 OBJECT IDENTIFIER ::= { ciscoProducts 6 }
cisco4000 OBJECT IDENTIFIER ::= { ciscoProducts 7 }
cisco7000 OBJECT IDENTIFIER ::= { ciscoProducts 8 }
ciscoCS500 OBJECT IDENTIFIER ::= { ciscoProducts 9 }
cisco2000 OBJECT IDENTIFIER ::= { ciscoProducts 10 }

-- note well that an AGS+ must contain a cBus controller in order to
-- know that it is an AGS+, otherwise it is unable to determine what
-- kind of device it is, and returns one of the functionality-based
-- sysObjectID values from above
ciscoAGSplus OBJECT IDENTIFIER ::= { ciscoProducts 11 }

cisco7010 OBJECT IDENTIFIER ::= { ciscoProducts 12 }
cisco2500 OBJECT IDENTIFIER ::= { ciscoProducts 13 }
cisco4500 OBJECT IDENTIFIER ::= { ciscoProducts 14 }
cisco2102 OBJECT IDENTIFIER ::= { ciscoProducts 15 }
cisco2202 OBJECT IDENTIFIER ::= { ciscoProducts 16 }
cisco2501 OBJECT IDENTIFIER ::= { ciscoProducts 17 }
cisco2502 OBJECT IDENTIFIER ::= { ciscoProducts 18 }
cisco2503 OBJECT IDENTIFIER ::= { ciscoProducts 19 }
cisco2504 OBJECT IDENTIFIER ::= { ciscoProducts 20 }
cisco2505 OBJECT IDENTIFIER ::= { ciscoProducts 21 }
cisco2506 OBJECT IDENTIFIER ::= { ciscoProducts 22 }
cisco2507 OBJECT IDENTIFIER ::= { ciscoProducts 23 }
cisco2508 OBJECT IDENTIFIER ::= { ciscoProducts 24 }
cisco2509 OBJECT IDENTIFIER ::= { ciscoProducts 25 }
cisco2510 OBJECT IDENTIFIER ::= { ciscoProducts 26 }
cisco2511 OBJECT IDENTIFIER ::= { ciscoProducts 27 }
cisco2512 OBJECT IDENTIFIER ::= { ciscoProducts 28 }
cisco2513 OBJECT IDENTIFIER ::= { ciscoProducts 29 }
cisco2514 OBJECT IDENTIFIER ::= { ciscoProducts 30 }
cisco2515 OBJECT IDENTIFIER ::= { ciscoProducts 31 }
cisco3101 OBJECT IDENTIFIER ::= { ciscoProducts 32 }
cisco3102 OBJECT IDENTIFIER ::= { ciscoProducts 33 }
cisco3103 OBJECT IDENTIFIER ::= { ciscoProducts 34 }
cisco3104 OBJECT IDENTIFIER ::= { ciscoProducts 35 }
cisco3202 OBJECT IDENTIFIER ::= { ciscoProducts 36 }
cisco3204 OBJECT IDENTIFIER ::= { ciscoProducts 37 }
ciscoAccessProRC OBJECT IDENTIFIER ::= { ciscoProducts 38 }
ciscoAccessProEC OBJECT IDENTIFIER ::= { ciscoProducts 39 }
cisco1000 OBJECT IDENTIFIER ::= { ciscoProducts 40 }
cisco1003 OBJECT IDENTIFIER ::= { ciscoProducts 41 }
cisco2516 OBJECT IDENTIFIER ::= { ciscoProducts 42 }
cisco1020 OBJECT IDENTIFIER ::= { ciscoProducts 43 }
cisco1004 OBJECT IDENTIFIER ::= { ciscoProducts 44 }
cisco7507 OBJECT IDENTIFIER ::= { ciscoProducts 45 }
cisco7513 OBJECT IDENTIFIER ::= { ciscoProducts 46 }
cisco7506 OBJECT IDENTIFIER ::= { ciscoProducts 47 }	
cisco7505 OBJECT IDENTIFIER ::= { ciscoProducts 48 }
cisco1005 OBJECT IDENTIFIER ::= { ciscoProducts 49 }
cisco4700 OBJECT IDENTIFIER ::= { ciscoProducts 50 }
ciscoPro1003 OBJECT IDENTIFIER ::= { ciscoProducts 51 }
ciscoPro1004 OBJECT IDENTIFIER ::= { ciscoProducts 52 }
ciscoPro1005 OBJECT IDENTIFIER ::= { ciscoProducts 53 }
ciscoPro1020 OBJECT IDENTIFIER ::= { ciscoProducts 54 }	
ciscoPro2500PCE OBJECT IDENTIFIER ::= { ciscoProducts 55 }
ciscoPro2501 OBJECT IDENTIFIER ::= { ciscoProducts 56 }
ciscoPro2503 OBJECT IDENTIFIER ::= { ciscoProducts 57 }
ciscoPro2505 OBJECT IDENTIFIER ::= { ciscoProducts 58 }
ciscoPro2507 OBJECT IDENTIFIER ::= { ciscoProducts 59 }
ciscoPro2509 OBJECT IDENTIFIER ::= { ciscoProducts 60 }
ciscoPro2511 OBJECT IDENTIFIER ::= { ciscoProducts 61 }
ciscoPro2514 OBJECT IDENTIFIER ::= { ciscoProducts 62 }
ciscoPro2516 OBJECT IDENTIFIER ::= { ciscoProducts 63 }
ciscoPro2519 OBJECT IDENTIFIER ::= { ciscoProducts 64 }
ciscoPro2521 OBJECT IDENTIFIER ::= { ciscoProducts 65 }	
ciscoPro4500 OBJECT IDENTIFIER ::= { ciscoProducts 66 }
cisco2517 OBJECT IDENTIFIER ::= { ciscoProducts 67 }
cisco2518 OBJECT IDENTIFIER ::= { ciscoProducts 68 }
cisco2519 OBJECT IDENTIFIER ::= { ciscoProducts 69 }
cisco2520 OBJECT IDENTIFIER ::= { ciscoProducts 70 }
cisco2521 OBJECT IDENTIFIER ::= { ciscoProducts 71 }
cisco2522 OBJECT IDENTIFIER ::= { ciscoProducts 72 }
cisco2523 OBJECT IDENTIFIER ::= { ciscoProducts 73 }
cisco2524 OBJECT IDENTIFIER ::= { ciscoProducts 74 }
cisco2525 OBJECT IDENTIFIER ::= { ciscoProducts 75 }
ciscoPro751 OBJECT IDENTIFIER ::= { ciscoProducts 76 }
ciscoPro752 OBJECT IDENTIFIER ::= { ciscoProducts 77 }
ciscoPro753 OBJECT IDENTIFIER ::= { ciscoProducts 78 }
cisco751 OBJECT IDENTIFIER ::= { ciscoProducts 81 }
cisco752 OBJECT IDENTIFIER ::= { ciscoProducts 82 }
cisco753 OBJECT IDENTIFIER ::= { ciscoProducts 83 }
ciscoPro741 OBJECT IDENTIFIER ::= { ciscoProducts 84 }
ciscoPro742 OBJECT IDENTIFIER ::= { ciscoProducts 85 }	
ciscoPro743 OBJECT IDENTIFIER ::= { ciscoProducts 86 }	
ciscoPro744 OBJECT IDENTIFIER ::= { ciscoProducts 87 }	
ciscoPro761 OBJECT IDENTIFIER ::= { ciscoProducts 88 }	
ciscoPro762 OBJECT IDENTIFIER ::= { ciscoProducts 89 }	
ciscoPro765 OBJECT IDENTIFIER ::= { ciscoProducts 92 }
ciscoPro766 OBJECT IDENTIFIER ::= { ciscoProducts 93 }
cisco741 OBJECT IDENTIFIER ::= { ciscoProducts 94 }	
cisco742 OBJECT IDENTIFIER ::= { ciscoProducts 95 }
cisco743 OBJECT IDENTIFIER ::= { ciscoProducts 96 }	
cisco744 OBJECT IDENTIFIER ::= { ciscoProducts 97 }	
cisco761 OBJECT IDENTIFIER ::= { ciscoProducts 98 }
cisco762 OBJECT IDENTIFIER ::= { ciscoProducts 99 }
cisco765 OBJECT IDENTIFIER ::= { ciscoProducts 102 }
cisco766 OBJECT IDENTIFIER ::= { ciscoProducts 103 }
ciscoPro2520 OBJECT IDENTIFIER ::= { ciscoProducts 104 }
ciscoPro2522 OBJECT IDENTIFIER ::= { ciscoProducts 105 }
ciscoPro2524 OBJECT IDENTIFIER ::= { ciscoProducts 106 }
ciscoLS1010 OBJECT IDENTIFIER ::= { ciscoProducts 107 }
cisco7206 OBJECT IDENTIFIER ::= { ciscoProducts 108 }
ciscoAS5200 OBJECT IDENTIFIER ::= { ciscoProducts 109 }
cisco3640 OBJECT IDENTIFIER ::= { ciscoProducts 110 }
ciscoCatalyst3500 OBJECT IDENTIFIER ::= { ciscoProducts 111 }	
ciscoWSX3011 OBJECT IDENTIFIER ::= { ciscoProducts 112 }	
cisco1601 OBJECT IDENTIFIER ::= { ciscoProducts 113 }
cisco1602 OBJECT IDENTIFIER ::= { ciscoProducts 114 }
cisco1603 OBJECT IDENTIFIER ::= { ciscoProducts 115 }
cisco1604 OBJECT IDENTIFIER ::= { ciscoProducts 116 }
ciscoPro1601 OBJECT IDENTIFIER ::= { ciscoProducts 117 }
ciscoPro1602 OBJECT IDENTIFIER ::= { ciscoProducts 118 }
ciscoPro1603 OBJECT IDENTIFIER ::= { ciscoProducts 119 }
ciscoPro1604 OBJECT IDENTIFIER ::= { ciscoProducts 120 }
cisco3620 OBJECT IDENTIFIER ::= { ciscoProducts 122 }
ciscoPro3620 OBJECT IDENTIFIER ::= { ciscoProducts 123 }	
ciscoPro3640 OBJECT IDENTIFIER ::= { ciscoProducts 124 }
cisco7204 OBJECT IDENTIFIER ::= { ciscoProducts 125 }
cisco771 OBJECT IDENTIFIER ::= { ciscoProducts 126 }	
cisco772 OBJECT IDENTIFIER ::= { ciscoProducts 127 }
cisco775 OBJECT IDENTIFIER ::= { ciscoProducts 128 }
cisco776 OBJECT IDENTIFIER ::= { ciscoProducts 129 }
ciscoPro2502 OBJECT IDENTIFIER ::= { ciscoProducts 130 }
ciscoPro2504 OBJECT IDENTIFIER ::= { ciscoProducts 131 }
ciscoPro2506 OBJECT IDENTIFIER ::= { ciscoProducts 132 }
ciscoPro2508 OBJECT IDENTIFIER ::= { ciscoProducts 133 }
ciscoPro2510 OBJECT IDENTIFIER ::= { ciscoProducts 134 }
ciscoPro2512 OBJECT IDENTIFIER ::= { ciscoProducts 135 }
ciscoPro2513 OBJECT IDENTIFIER ::= { ciscoProducts 136 }
ciscoPro2515 OBJECT IDENTIFIER ::= { ciscoProducts 137 }
ciscoPro2517 OBJECT IDENTIFIER ::= { ciscoProducts 138 }
ciscoPro2518 OBJECT IDENTIFIER ::= { ciscoProducts 139 }
ciscoPro2523 OBJECT IDENTIFIER ::= { ciscoProducts 140 }
ciscoPro2525 OBJECT IDENTIFIER ::= { ciscoProducts 141 }
ciscoPro4700 OBJECT IDENTIFIER ::= { ciscoProducts 142 }
ciscoPro316T OBJECT IDENTIFIER ::= { ciscoProducts 147 }
ciscoPro316C OBJECT IDENTIFIER ::= { ciscoProducts 148 }
ciscoPro3116 OBJECT IDENTIFIER ::= { ciscoProducts 149 }
catalyst116T OBJECT IDENTIFIER ::= { ciscoProducts 150 }
catalyst116C OBJECT IDENTIFIER ::= { ciscoProducts 151 }
catalyst1116 OBJECT IDENTIFIER ::= { ciscoProducts 152 }
ciscoAS2509RJ OBJECT IDENTIFIER ::= { ciscoProducts 153 }
ciscoAS2511RJ OBJECT IDENTIFIER ::= { ciscoProducts 154 }
ciscoMC3810 OBJECT IDENTIFIER ::= { ciscoProducts 157 }
cisco1503 OBJECT IDENTIFIER ::= { ciscoProducts 160 }
cisco1502 OBJECT IDENTIFIER ::= { ciscoProducts 161 }
ciscoAS5300 OBJECT IDENTIFIER ::= { ciscoProducts 162 }
ciscoLS1015 OBJECT IDENTIFIER ::= { ciscoProducts 164 }	
cisco2501FRADFX OBJECT IDENTIFIER ::= { ciscoProducts 165 }
cisco2501LANFRADFX OBJECT IDENTIFIER ::= { ciscoProducts 166 }
cisco2502LANFRADFX OBJECT IDENTIFIER ::= { ciscoProducts 167 }
ciscoWSX5302 OBJECT IDENTIFIER ::= { ciscoProducts 168 }
ciscoFastHub216T OBJECT IDENTIFIER ::= { ciscoProducts 169 }
catalyst2908xl OBJECT IDENTIFIER ::= { ciscoProducts 170 }		-- Catalyst 2908XL switch with 8 10/100BaseTX ports 
catalyst2916m-xl OBJECT IDENTIFIER ::= { ciscoProducts 171 }		-- Catalyst 2916M-XL switch with 16 10/100BaseTX ports and 2 uplink slots
cisco1605 OBJECT IDENTIFIER ::= { ciscoProducts 172 }
cisco12012 OBJECT IDENTIFIER ::= { ciscoProducts 173 }
catalyst1912C OBJECT IDENTIFIER ::= { ciscoProducts 175 }
ciscoMicroWebServer2 OBJECT IDENTIFIER ::= { ciscoProducts 176 }
ciscoFastHubBMMTX OBJECT IDENTIFIER ::= { ciscoProducts 177 }
ciscoFastHubBMMFX OBJECT IDENTIFIER ::= { ciscoProducts 178 }
ciscoUBR7246 OBJECT IDENTIFIER ::= { ciscoProducts 179 }		-- Universal Broadband Router
cisco6400 OBJECT IDENTIFIER ::= { ciscoProducts 180 }
cisco12004 OBJECT IDENTIFIER ::= { ciscoProducts 181 }
cisco12008 OBJECT IDENTIFIER ::= { ciscoProducts 182 }
catalyst2924XL OBJECT IDENTIFIER ::= { ciscoProducts 183 }		-- Catalyst 2924XL switch with 24 10/100BaseTX ports; doesn't support port-based VLANs.
catalyst2924CXL OBJECT IDENTIFIER ::= { ciscoProducts 184 } 		-- Catalyst 2924C-XL switch; doesn't support port-based VLANs. 
cisco2610 OBJECT IDENTIFIER ::= { ciscoProducts 185 }			-- Cisco 2600 platform with 1 integrated ethernet interface
cisco2611 OBJECT IDENTIFIER ::= { ciscoProducts 186 }			-- Cisco 2600 platform with 2 integrated ethernet interfaces 
cisco2612 OBJECT IDENTIFIER ::= { ciscoProducts 187 }			-- Cisco 2600 platform with an integrated ethernet and token ring
ciscoAS5800 OBJECT IDENTIFIER ::= { ciscoProducts 188 }
ciscoSC3640 OBJECT IDENTIFIER ::= { ciscoProducts 189 }
cisco8510 OBJECT IDENTIFIER ::= { ciscoProducts 190 }			-- Cisco Catalyst 8510CSR (Campus Switching Router)
ciscoUBR904 OBJECT IDENTIFIER ::= { ciscoProducts 191 }			-- Cisco Cable Modem (UBR - Universal Broadband Router)
cisco6200 OBJECT IDENTIFIER ::= { ciscoProducts 192 }
cisco7202 OBJECT IDENTIFIER ::= { ciscoProducts 194 } 			-- Modular two slot router in the cisco7200 family 
cisco2613 OBJECT IDENTIFIER ::= { ciscoProducts 195 }			-- Cisco 2600 platform with 1 integrated token ring interface
cisco8515 OBJECT IDENTIFIER ::= { ciscoProducts 196 }			-- Cisco Catalyst 8515CSR (Campus Switching Router)
catalyst9006 OBJECT IDENTIFIER ::= { ciscoProducts 197 } 
catalyst9009 OBJECT IDENTIFIER ::= { ciscoProducts 198 }
ciscoRPM OBJECT IDENTIFIER ::= { ciscoProducts 199 }			-- Router Processor Module
cisco1710	OBJECT IDENTIFIER ::= { ciscoProducts 200 }		-- VPN(Virtual Private Network) Security Router with 1 FastEthernet and 1 Ethernet interface onboard
cisco1720 OBJECT IDENTIFIER ::= { ciscoProducts 201 }		
catalyst8540msr OBJECT IDENTIFIER ::= { ciscoProducts 202 }		-- Catalyst 8540 Multiservice Switching Router
catalyst8540csr OBJECT IDENTIFIER ::= { ciscoProducts 203 }		-- Catalyst 8540 Campus Switching Router
cisco7576 OBJECT IDENTIFIER ::= { ciscoProducts 204 }			-- Dual Independent RSP platform, 13 slots 
cisco3660 OBJECT IDENTIFIER ::= { ciscoProducts 205 }			-- Six slot MARs router 
cisco1401 OBJECT IDENTIFIER ::= { ciscoProducts 206 }			-- Router product with 1 ethernet and 1 ATM25 interface 
cisco2620 OBJECT IDENTIFIER ::= { ciscoProducts 208 }			-- Cisco 2600 chassis with 1 onboard FE
cisco2621 OBJECT IDENTIFIER ::= { ciscoProducts 209 }			-- Cisco 2600 chassis with 2 onboard 10/100 FE ports 
ciscoUBR7223 OBJECT IDENTIFIER ::= { ciscoProducts 210 }		-- Universal Broadband Router
cisco6400Nrp OBJECT IDENTIFIER ::= { ciscoProducts 211 }		-- Cisco 6400 Network Routing Processor 
cisco801 OBJECT IDENTIFIER ::= { ciscoProducts 212 }			-- Cisco 800 platform with 1 ethernet and 1 BRI S/T
cisco802 OBJECT IDENTIFIER ::= { ciscoProducts 213 }			-- Cisco 800 platform with 1 ethernet and 1 BRI U 
cisco803 OBJECT IDENTIFIER ::= { ciscoProducts 214 }			-- Cisco 800 platform with 1 ethernet 4-port HUB, 1 BRI S/T, and 2 POTs 
cisco804 OBJECT IDENTIFIER ::= { ciscoProducts 215 }			-- Cisco 800 platform with 1 ethernet 4-port HUB, 1 BRI U, and 2 POTs 
cisco1750 OBJECT IDENTIFIER ::= { ciscoProducts 216 }			-- VoIP (Voice over IP) capable Cisco 1700 platform with 2 WIC/VIC slots and 1 VIC-only slot
catalyst2924XLv OBJECT IDENTIFIER ::= { ciscoProducts 217 }		-- Catalyst 2924XL switch with 24 10BaseT/100BaseTX autosensing switch ports; supports port-based VLANs; can run Standard or Enterprise edition software.
catalyst2924CXLv OBJECT IDENTIFIER ::= { ciscoProducts 218 }		-- Catalyst 2924C-XL switch with 22 10BaseT/100BaseTX and 2 100BaseFX autosensing switch ports; supports port-based VLANs; can run Standard or Enterprise edition software.
catalyst2912XL OBJECT IDENTIFIER ::= { ciscoProducts 219 }		-- Catalyst 2912XL switch with 12 autosensing 10/100BaseTX ports, can run Standard or Enterprise edition software. 
catalyst2924MXL OBJECT IDENTIFIER ::= { ciscoProducts 220 }		-- Catalyst 2924M-XL switch with 24 autosensing 10/100BaseTX ports and 2 uplink slots, can run Standard or Enterprise edition software.
catalyst2912MfXL OBJECT IDENTIFIER ::= { ciscoProducts 221 }		-- Catalyst 2912MF-XL switch with 12 100BaseFX ports and 2 uplink slots; can only run Enterprise edition software.
cisco7206VXR OBJECT IDENTIFIER ::= { ciscoProducts 222 }		-- Cisco 7200 platform, VXR series chassis with 6 slots 
cisco7204VXR OBJECT IDENTIFIER ::= { ciscoProducts 223 }		-- Cisco 7200 platform, VXR series chassis with 4 slots
cisco1538M OBJECT IDENTIFIER ::= { ciscoProducts 224 }		-- Cisco Network Office 8-port 10/100 Repeater
cisco1548M OBJECT IDENTIFIER ::= { ciscoProducts 225 }		-- Cisco Network Office 10/100 Switch
ciscoFasthub100 OBJECT IDENTIFIER ::= { ciscoProducts 226 }		-- Cisco Fast Hub 100 Series 10/100 Repeater
ciscoPIXFirewall OBJECT IDENTIFIER ::= { ciscoProducts 227 }		-- Cisco PIX Firewall
ciscoMGX8850 OBJECT IDENTIFIER ::= { ciscoProducts 228 }		-- Cisco Multiservice Gigabit Switch with 32 half height slots 
ciscoMGX8830 OBJECT IDENTIFIER ::= { ciscoProducts 229 }		-- Cisco Multiservice Switch with 16 half-height slots
-- ciscoMGX8820 OBJECT IDENTIFIER ::= { ciscoProducts 229 }
catalyst8510msr OBJECT IDENTIFIER ::= { ciscoProducts 230 }		-- Catalyst ATM 8510 Multiservice Switching Router 
catalyst8515msr OBJECT IDENTIFIER ::= { ciscoProducts 231 }		-- Catalyst ATM 8515 Multiservice Switching Router
ciscoIGX8410 OBJECT IDENTIFIER ::= { ciscoProducts 232 }		-- Cisco IGX8400 (Integrated Gigabit eXchange) series wide-area switch with 8 slots 
ciscoIGX8420 OBJECT IDENTIFIER ::= { ciscoProducts 233 }		-- Cisco IGX8400 (Integrated Gigabit eXchange) series wide-area switch with 16 slots 
ciscoIGX8430 OBJECT IDENTIFIER ::= { ciscoProducts 234 }		-- Cisco IGX8400 (Integrated Gigabit eXchange) series wide-area switch with 32 slots
ciscoIGX8450 OBJECT IDENTIFIER ::= { ciscoProducts 235 }		-- Cisco IGX8400 (Integrated Gigabit eXchange) series wide-area switch with integrated MGX feeder 
ciscoBPX8620 OBJECT IDENTIFIER ::= { ciscoProducts 237 }		-- Cisco BPX8600 (Broadband Packet eXchange) series basic wide-area switch with 15 slots
ciscoBPX8650 OBJECT IDENTIFIER ::= { ciscoProducts 238 }		-- Cisco BPX8600 (Broadband Packet eXchange) series wide-area switch with integrated tag switching controller and 15 slots 
ciscoBPX8680 OBJECT IDENTIFIER ::= { ciscoProducts 239 }		-- Cisco BPX8600 (Broadband Packet eXchange) series wide-area switch with integrated MGX feeder and 15 slots 
ciscoCacheEngine OBJECT IDENTIFIER ::= { ciscoProducts 240 }		-- Cisco Cache Engine
ciscoCat6000 OBJECT IDENTIFIER ::= { ciscoProducts 241 }		-- Cisco Catalyst 6000 
ciscoBPXSes OBJECT IDENTIFIER ::= { ciscoProducts 242 }		-- Cisco BPX (Broadband Packet eXchange) Service Expansion Slot controller
ciscoIGXSes OBJECT IDENTIFIER ::= { ciscoProducts 243 }		-- Cisco IGX (Integrated Gigabit eXchange) Service Expansion Slot controller/feeder, used in IGX8410/IGX8420/IGX8430 switches. 
ciscoLocalDirector OBJECT IDENTIFIER ::= { ciscoProducts 244 }	-- Cisco Local Director
cisco805 OBJECT IDENTIFIER ::= { ciscoProducts 245 }			-- Cisco 800 platform with 1 ethernet and 1 serial WIC 
catalyst3508GXL OBJECT IDENTIFIER ::= { ciscoProducts 246 }		-- Cisco Catalyst 3508G-XL switch with 8 GBIC Gigabit ports, can run Standard or Enterprise edition software. 
catalyst3512XL OBJECT IDENTIFIER ::= { ciscoProducts 247 }		-- Cisco Catalyst 3512XL switch with 12 10/100BaseTX ports and 2 GBIC Gigabit ports, can run Standard or Enterprise edition software. 
catalyst3524XL OBJECT IDENTIFIER ::= { ciscoProducts 248 }		-- Cisco Catalyst 3524XL switch with 24 10/100BaseTX ports and 2 GBIC Gigabit ports, can run Standard or Enterprise edition software. 
cisco1407 OBJECT IDENTIFIER ::= { ciscoProducts 249 }			-- Cisco 1400 series router with 1 Ethernet and 1 ADSL interface, with 1407 chipset
cisco1417 OBJECT IDENTIFIER ::= { ciscoProducts 250 }			-- Cisco 1400 series router with 1 Ethernet and 1 ADSL interface, with 1417 chipset 
cisco6100 OBJECT IDENTIFIER ::= { ciscoProducts 251 }			-- Cisco 6100 DSLAM Chassis
cisco6130 OBJECT IDENTIFIER ::= { ciscoProducts 252 }			-- Cisco 6130 DSLAM Chassis
cisco6260 OBJECT IDENTIFIER ::= { ciscoProducts 253 }			-- Cisco 6260 DSLAM Chassis
ciscoOpticalRegenerator OBJECT IDENTIFIER ::= { ciscoProducts 254 }	-- Cisco Optical Regenerator 
ciscoUBR924 OBJECT IDENTIFIER ::= { ciscoProducts 255 }		-- Cisco UBR Cable Modem which is a UBR904 with 2 FXS Voice ports 
ciscoWSX6302Msm OBJECT IDENTIFIER ::= { ciscoProducts 256 }             -- Catalyst 6000 or 6500 Series Multilayer Switch Module WS-X6302-MSM that directly interfaces to the switch's backplane to provide layer 3 switching.
catalyst5kRsfc OBJECT IDENTIFIER ::= { ciscoProducts 257 }		-- Router Switching Feature Card for the Catalyst 5000 that is treated as a standalone system by the NMS 
catalyst6kMsfc  OBJECT IDENTIFIER ::= { ciscoProducts 258 }      -- Multilevel Switching Feature Card for Catalyst 6000 that is treated as a standalone system by the NMS
cisco7120Quadt1 OBJECT IDENTIFIER ::= { ciscoProducts 259 }		-- 7120 Series chassis with 2 10/100 FE interfaces, 4 T1/E1 interfaces 
cisco7120T3 OBJECT IDENTIFIER ::= { ciscoProducts 260 }		-- 7120 Series chassis with 2 10/100 FE interfaces, 1 T3 interface 
cisco7120E3 OBJECT IDENTIFIER ::= { ciscoProducts 261 }		-- 7120 Series chassis with 2 10/100 FE interfaces, 1 E3 interface 
cisco7120At3 OBJECT IDENTIFIER ::= { ciscoProducts 262 }		-- 7120 Series chassis with 2 10/100 FE interfaces, 1 T3 ATM interface 
cisco7120Ae3 OBJECT IDENTIFIER ::= { ciscoProducts 263 }		-- 7120 Series chassis with 2 10/100 FE interfaces, 1 E3 ATM interface 
cisco7120Smi3 OBJECT IDENTIFIER ::= { ciscoProducts 264 }		-- 7120 Series chassis with 2 10/100 FE interfaces, 1 OC3SMI ATM interface 
cisco7140Dualt3 OBJECT IDENTIFIER ::= { ciscoProducts 265 }		-- 7140 Series chassis with 2 10/100 FE interfaces, 2 T3 interfaces 
cisco7140Duale3 OBJECT IDENTIFIER ::= { ciscoProducts 266 }		-- 7140 Series chassis with 2 10/100 FE interfaces, 2 E3 interfaces 
cisco7140Dualat3 OBJECT IDENTIFIER ::= { ciscoProducts 267 }		-- 7140 Series chassis with 2 10/100 FE interfaces, 2 T3 ATM interfaces 
cisco7140Dualae3 OBJECT IDENTIFIER ::= { ciscoProducts 268 }		-- 7140 Series chassis with 2 10/100 FE interfaces, 2 E3 ATM interfaces 
cisco7140Dualmm3 OBJECT IDENTIFIER ::= { ciscoProducts 269 }		-- 7140 Series chassis with 2 10/100 FE interfaces, 2 OC3MM ATM interfaces 
cisco827QuadV OBJECT IDENTIFIER ::= { ciscoProducts 270 }		-- Cisco 800 platform with 1 ethernet, 1 ADSL DMT issue 2, and 4 voice POTS FXS ports
ciscoUBR7246VXR OBJECT IDENTIFIER ::= { ciscoProducts 271 }           -- Cisco 7246 Universal Broadband Router, VXR series
cisco10400 OBJECT IDENTIFIER ::= { ciscoProducts 272 }		-- Cisco 10000 platform with 10 slots
cisco12016 OBJECT IDENTIFIER ::= { ciscoProducts 273 }		-- Cisco 12000 platform with 16 slots
ciscoAs5400 OBJECT IDENTIFIER ::= { ciscoProducts 274 }		-- Cisco AS5400 platform
cat2948gL3 OBJECT IDENTIFIER ::= { ciscoProducts 275 }		-- Cisco Catalyst WS-C2948G-L3 48 port 10/100 Layer 3 switch with 2 GBIC ports
cisco7140Octt1 OBJECT IDENTIFIER ::= { ciscoProducts 276 }		-- 7140 Series chassis with 8 integrated T1/E1 serial ports
cisco7140Dualfe OBJECT IDENTIFIER ::= { ciscoProducts 277 }		-- 7140 Series chassis with 2 integrated 10/100 FE interfaces
cat3548XL OBJECT IDENTIFIER ::= { ciscoProducts 278 }			-- Catalyst 3548XL switch (WS-C3548-XL)
ciscoVG200 OBJECT IDENTIFIER ::= { ciscoProducts 279 }		-- Cisco Voice Gateway 200 controlled by Cisco Call Manager
cat6006 OBJECT IDENTIFIER ::= { ciscoProducts 280 }			-- Catalyst 6000 with 6 slots
cat6009 OBJECT IDENTIFIER ::= { ciscoProducts 281 }			-- Catalyst 6000 with 9 slots
cat6506 OBJECT IDENTIFIER ::= { ciscoProducts 282 }			-- Catalyst 6000 Plus with 6 slots
cat6509 OBJECT IDENTIFIER ::= { ciscoProducts 283 }			-- Catalyst 6000 Plus with 9 slots
cisco827 OBJECT IDENTIFIER ::= { ciscoProducts 284 }			-- Cisco 800 platform with 1 ethernet, 1 ADSL DMT issue 2
ciscoManagementEngine1100 OBJECT IDENTIFIER ::= { ciscoProducts 285 }	-- Cisco Management Engine 1100 for doing distributed SNMP polling
ciscoMc3810V3 OBJECT IDENTIFIER ::= { ciscoProducts 286 }		-- Cisco MC3810-V3, capable of data, voice and video.  Supports 2 additional ports than the MC3810-V, used for optional access cards.
cat3524tXLEn OBJECT IDENTIFIER ::= { ciscoProducts 287 }		-- Cisco Catalyst 3524 switch (WS-C3524T-XL-EN) with 24 10/100 ports and 2 GBIC gigabit ports.  Runs Enterprise edition software and provides telephony power to attached IP telephones
cisco7507z OBJECT IDENTIFIER ::= { ciscoProducts 288 }		-- Cisco 7507z chassis, Czbus capable, 7 slots
cisco7513z OBJECT IDENTIFIER ::= { ciscoProducts 289 }		-- Cisco 7513z chassis, Czbus capable, 13 slots
cisco7507mx OBJECT IDENTIFIER ::= { ciscoProducts 290 }		-- Cisco 7507mx chassis, Czbus capable, TDM (Time Division Multiplexing) backplane support, 7 slots
cisco7513mx OBJECT IDENTIFIER ::= { ciscoProducts 291 }		-- Cisco 7513mx chassis, Czbus capable, TDM (Time Division Multiplexing) backplane support, 13 slots
ciscoUBR912C OBJECT IDENTIFIER ::= { ciscoProducts 292 }		-- Cisco uBR912-C Cable Modem with CSU/DSU WIC
ciscoUBR912S OBJECT IDENTIFIER ::= { ciscoProducts 293 }		-- Cisco uBR912-S Cable Modem with Serial WIC
ciscoUBR914 OBJECT IDENTIFIER ::= { ciscoProducts 294 }		-- Cisco uBR914 Cable Modem with removable WIC
cisco802J OBJECT IDENTIFIER ::= { ciscoProducts 295 }			-- Cisco 800 platform with 1 ethernet, 1 BRI S/T, and 1 Japanese BRI U
cisco804J OBJECT IDENTIFIER ::= { ciscoProducts 296 }			-- Cisco 800 platform with 1 ethernet, 2 POTS, 1 BRI/ST, and 1 Japanese BRI U
cisco6160 OBJECT IDENTIFIER ::= { ciscoProducts 297 }			-- Cisco 6160 DSLAM chassis
cat4908gL3 OBJECT IDENTIFIER ::= { ciscoProducts 298 }		-- Catalyst 4908G-L3 (WS-C4908G-L3) Mid-range fixed configuration layer 3 switch with 6 GBIC based Gigabit Ethernet ports
cisco6015 OBJECT IDENTIFIER ::= { ciscoProducts 299 }			-- Cisco 6015 DSLAM chassis
cat4232L3 OBJECT IDENTIFIER ::= { ciscoProducts 300 }		-- Cisco Catalyst 4232-L3 layer 3 line card that is treated as a standalone system by the NMS
catalyst6kMsfc2  OBJECT IDENTIFIER ::= { ciscoProducts 301 }      -- Multilevel Switching Feature Card Version 2 for Catalyst 6000 that is treated as a standalone system by the NMS
cisco7750Mrp200 OBJECT IDENTIFIER ::= { ciscoProducts 302 }			-- Cisco ICS 7750 Multiservice Route Processor 200
cisco7750Ssp80 OBJECT IDENTIFIER ::= { ciscoProducts 303 }			-- Cisco ICS 7750 System Switch Processor 80
ciscoMGX8230 OBJECT IDENTIFIER ::= { ciscoProducts 304 }		-- Multi Service Switch with 16 half-height slots 
ciscoMGX8250 OBJECT IDENTIFIER ::= { ciscoProducts 305 }		-- Multi Service Switch with 32 half-height slots 
ciscoCVA122 OBJECT IDENTIFIER ::= { ciscoProducts 306 }		-- Cisco CVA122 Cable Voice Adapter (Residential Cable Modem with two Voice Ports) 
ciscoCVA124 OBJECT IDENTIFIER ::= { ciscoProducts 307 }		-- Cisco CVA124 Cable Voice Adapter (Residential Cable Modem with four Voice Ports)
ciscoAs5850 OBJECT IDENTIFIER ::= { ciscoProducts 308 }		-- High End Dial Access Server
cat6509Sp OBJECT IDENTIFIER ::= { ciscoProducts 310 }		-- 9-slot Constellation+ vertical slot chassis
ciscoMGX8240 OBJECT IDENTIFIER ::= { ciscoProducts 311 }	-- High Density Circuit Emulation Service Gateway for Private Line Service
cat4840gL3 OBJECT IDENTIFIER ::= { ciscoProducts 312 }		--  Catalyst 4840G-L3 (WS-C4840G) Layer 3 Ethernet Switching System with Server Load Balancing
ciscoAS5350 OBJECT IDENTIFIER ::= { ciscoProducts 313 }		--  Cisco low end Access server platform
cisco7750 OBJECT IDENTIFIER ::= { ciscoProducts 314 }		--  Cisco Integrated Communication System (ICS) 7750
ciscoMGX8950 OBJECT IDENTIFIER ::= { ciscoProducts 315 }		--  Multiservice Gigabit Switch(180Gb switch) with 32 half height slots 
ciscoUBR925 OBJECT IDENTIFIER ::= { ciscoProducts 316 }		-- Cisco UBR925 Cable Modem/Router with VOIP and hardware accelerated IPSEC
ciscoUBR10012 OBJECT IDENTIFIER ::= { ciscoProducts 317 }	-- Cisco uBR10000 platform with 8 broadband slots and 4 WAN slots
catalyst4kGateway OBJECT IDENTIFIER ::= { ciscoProducts 318 }	-- Catalyst 4000 Access Gateway line card supporting voice and WAN (Wide Area Network) interfaces as well as conferencing and transcoding services for operation with the Cisco Call Manager
cisco2650 OBJECT IDENTIFIER ::= { ciscoProducts 319 }		-- c2650 platform with 1 integrated fast ethernet interface 
cisco2651 OBJECT IDENTIFIER ::= { ciscoProducts 320 }		-- c2650 platform with 2 integrated fast ethernet interfaces	
cisco826QuadV OBJECT IDENTIFIER ::= { ciscoProducts 321 }	-- Cisco 800 platform with 1 ethernet, 1 ADSL over ISDN and 4 voice POTS FXS ports
cisco826 OBJECT IDENTIFIER ::= { ciscoProducts 322 }		-- Cisco 800 platform with 1 ethernet, 1 ADSL over ISDN 
catalyst295012 OBJECT IDENTIFIER ::= { ciscoProducts 323 }	-- Cisco Catalyst c2950 switch  with 12 10/100BaseTX ports (WS-c2950-12)
catalyst295024 OBJECT IDENTIFIER ::= { ciscoProducts 324 }	-- Cisco Catalyst c2950 switch with 24 10/100 BaseTX ports (WS-c2950-24)
catalyst295024C OBJECT IDENTIFIER ::= { ciscoProducts 325 }	-- Cisco Catalyst c2950 switch with 24 10/100 BaseTX ports and 2 100BASE-FX uplink ports (WS-c2950C-24)
cisco1751 OBJECT IDENTIFIER ::= { ciscoProducts 326 }		-- Digital voice capable Cisco 1700 platform with 2 WIC/VIC slots and 1 VIC-only slot 
cisco626 OBJECT IDENTIFIER ::= { ciscoProducts 329 }		-- Cisco 600 DSL CPE pltaform with ADSL, DMT issue 1, 25M ATM interface
cisco627 OBJECT IDENTIFIER ::= { ciscoProducts 330 }		-- Cisco 600 DSL CPE pltaform with ADSL, DMT issue 2, 25M ATM interface
cisco633 OBJECT IDENTIFIER ::= { ciscoProducts 331 }		-- Cisco 600 DSL CPE platform with SDSL, 2B1Q line coding, serial interface (V.35/X.21)
cisco673 OBJECT IDENTIFIER ::= { ciscoProducts 332 }		-- Cisco 600 DSL CPE platform with SDSL, 2B1Q line coding, ethernet interface
cisco675 OBJECT IDENTIFIER ::= { ciscoProducts 333 }		-- Cisco 600 DSL CPE platform with ADSL, CAP, ethernet interface, POTS connector
cisco675e OBJECT IDENTIFIER ::= { ciscoProducts 334 }		-- Cisco 600 DSL CPE platform with ADSL, CAP, ethernet interface, universal power supply
cisco676 OBJECT IDENTIFIER ::= { ciscoProducts 335 }		-- Cisco 600 DSL CPE platform with ADSL, DMT issue 1, ethernet interface
cisco677 OBJECT IDENTIFIER ::= { ciscoProducts 336 }		-- Cisco 600 DSL CPE platform with ADSL, DMT issue 2, ethernet interface
cisco678 OBJECT IDENTIFIER ::= { ciscoProducts 337 }		-- Cisco 600 DSL CPE platform with ADSL, CAP/DMT/G.Lite, ethernet interface
cisco3661Ac OBJECT IDENTIFIER ::= { ciscoProducts 338 }		-- 1 Fast Ethernet version of c3660 with a AC power supply
cisco3661Dc OBJECT IDENTIFIER ::= { ciscoProducts 339 }		-- 1 Fast Ethernet version of c3660 with a DC power supply
cisco3662Ac OBJECT IDENTIFIER ::= { ciscoProducts 340 }		-- 2 Fast Ethernet version of c3660 with a AC power supply
cisco3662Dc OBJECT IDENTIFIER ::= { ciscoProducts 341 }		-- 2 Fast Ethernet version of c3660 with a DC power supply
cisco3662AcCo OBJECT IDENTIFIER ::= { ciscoProducts 342 }		-- 2 Fast Ethernet version of c3660 with a AC power supply for Telco's
cisco3662DcCo OBJECT IDENTIFIER ::= { ciscoProducts 343 }		-- 2 Fast Ethernet version of c3660 with a DC power supply for Telco's
ciscoUBR7111 OBJECT IDENTIFIER ::= { ciscoProducts 344 }	-- Low-end version of the Universal Broadband Router with 1 PA slot, 1 fixed RF line card (MC11C) and integrated upconvertor, designed for hotels, MDUs and smaller cable operators
ciscoUBR7111E OBJECT IDENTIFIER ::= { ciscoProducts 345 }	-- Low-end version of the Universal Broadband Router with 1 PA slot, 1 fixed RF line card (MC11E) and integrated upconvertor, designed for hotels, MDUs and smaller cable operators
ciscoUBR7114 OBJECT IDENTIFIER ::= { ciscoProducts 346 }	-- Low-end version of the Universal Broadband Router with 1 PA slot, 1 fixed RF line card (MC14C) and integrated upconvertor, designed for hotels, MDUs and smaller cable operators
ciscoUBR7114E OBJECT IDENTIFIER ::= { ciscoProducts 347 }	-- Low-end version of the Universal Broadband Router with 1 PA slot, 1 fixed RF line card (MC14E) and integrated upconvertor, designed for hotels, MDUs and smaller cable operators
cisco12010 OBJECT IDENTIFIER ::= { ciscoProducts 348 }	-- Cisco 12000 platform with 10 slots
cisco8110 OBJECT IDENTIFIER ::= { ciscoProducts 349 }	-- Cisco 8110 (ATM network termination device) with 3 Line Interface module slots
ciscoUBR905 OBJECT IDENTIFIER ::= { ciscoProducts 351 }	-- Cisco uBR905 Cable Modem with hardware accelerated IPSEC
ciscoSOHO77 OBJECT IDENTIFIER ::= { ciscoProducts 353 }    -- Cisco SOHO (Small Office Home Office) ADSL Router, 1 Ethernet and 1 ADSL G.992.1 (G.DMT) and G.992.2 (G.Lite) Interface
ciscoSOHO76 OBJECT IDENTIFIER ::= { ciscoProducts 354 }    -- Cisco SOHO (Small Office Home Office) ADSL over ISDN Router, 1 Ethernet and 1 ADSL ETSI/ITU-T G.992.1 Annex B (G.DMT) Interface
cisco7150Dualfe OBJECT IDENTIFIER ::= { ciscoProducts 355 }	-- 7150 Series chassis with 2 integrated 10/100 FE interfaces
cisco7150Octt1 OBJECT IDENTIFIER ::= { ciscoProducts 356 }	-- 7150 Series chassis with 8 integrated T1/E1 serial ports
cisco7150Dualt3 OBJECT IDENTIFIER ::= { ciscoProducts 357 }	-- 7150 Series chassis with 2 10/100 FE interfaces, 2 T3 interfaces
ciscoOlympus OBJECT IDENTIFIER ::= { ciscoProducts 358 } 	-- Cisco VPN (Virtual Private Network) Router with  4 10/100/1000 Gigabitethernet integrated interfaces 
catalyst2950t24 OBJECT IDENTIFIER ::= { ciscoProducts 359 }	-- Cisco Catalyst c2950 switch with 24 10/100BaseT ports and 2 10/100/1000BaseT ports 
ciscoVPS1110 OBJECT IDENTIFIER ::= { ciscoProducts 360 }	-- Cisco VLAN Policy Server 1110 manages VLAN-based policies to control user access to a LAN, leveraging existing authentication mechanisms such as Windows Domain Controllers and Novell's NDS. This policy server is part of CiscoWorks2000 User Registration Tool product.
ciscoContentEngine OBJECT IDENTIFIER ::= { ciscoProducts 361 }	-- Cisco Content Engine.  The Cisco Content Engine is a Content Networking product that accelerates content delivery, ensuring maximum scalability and availability of content.  The Content Engines offer caching, Content Delivery Network (CDN) services, employee internet management (e.g., URL filtering) and proxy services
ciscoIAD2420 OBJECT IDENTIFIER ::= { ciscoProducts 362 }	-- Integrated Access Device 2420 (IAD2420) chassis with Analog (8/16) FXS ports with T1 or ADSL (Asymmetrical Digital Subscriber Line) Uplinks
cisco677i OBJECT IDENTIFIER ::= { ciscoProducts 363 }		-- Cisco 600 DSL CPE platform with ASDL, DMT issue 2 over ISDN, ethernet interface
cisco674 OBJECT IDENTIFIER ::= { ciscoProducts 364 }		-- Cisco 600 DSL CPE platform with G.SHDSL, ethernet interface
ciscoDPA7630 OBJECT IDENTIFIER ::= { ciscoProducts 365 }	-- The Cisco Digital PBX Adapter (DPA) enables the integration of Cisco Call Manager with Octel voice mail systems
catalyst355024 OBJECT IDENTIFIER ::= { ciscoProducts 366 }	--  Catalyst 3550 24 10/100 ports + 2 Gig uplinks fixed configuration Layer 2/Layer 3 Ethernet Switch 
catalyst355048 OBJECT IDENTIFIER ::= { ciscoProducts 367 }	--  Catalyst 3550 48 10/100 ports + 2 Gig uplinks fixed configuration Layer 2/Layer 3 Ethernet Switch 
catalyst355012T OBJECT IDENTIFIER ::= { ciscoProducts 368 }	--  Catalyst 3550 12 1000T ports fixed configuration Layer 2/Layer 3 Ethernet Switch
catalyst2924LREXL OBJECT IDENTIFIER ::= { ciscoProducts 369 }	--  Cisco Catalyst c2924XL switch (WS-C2924-LRE-XL) with 24 10BaseS VDSL ports and 4 10/100BaseTX ports
catalyst2912LREXL OBJECT IDENTIFIER ::= { ciscoProducts 370 }	--  Cisco Catalyst c2912XL switch (WS-C2912-LRE-XL) with 12 10BaseS VDSL ports and 4 10/100BaseTX ports
ciscoCVA122E OBJECT IDENTIFIER ::= { ciscoProducts 371 }	-- Cisco CVA122-e Cable Voice Adapter(Residential Cable Modem with two voice ports)- European version
ciscoCVA124E OBJECT IDENTIFIER ::= { ciscoProducts 372 }	-- Cisco CVA124-e Cable Voice Adapter(Residential Cable Modem with four voice ports)- European version
ciscoURM OBJECT IDENTIFIER ::= { ciscoProducts 373 }		-- Universal Router Module for the IGX platform
ciscoURM2FE OBJECT IDENTIFIER ::= { ciscoProducts 374 }		-- Universal router module with 2 Fast Ethernet interfaces for IGX platform
ciscoURM2FE2V OBJECT IDENTIFIER ::= { ciscoProducts 375 }	-- Universal Router Module, with 2 Fast Ethernet ports, and 2 digital voice ports (T1 or E1)
cisco7401VXR OBJECT IDENTIFIER ::= { ciscoProducts 376 }	-- Cisco 7400 Family, 1 Slot router 
ciscoCAP340 OBJECT IDENTIFIER ::= { ciscoProducts 379 }		-- Aironet Wireless LAN Access Point 340 series
ciscoCAP350 OBJECT IDENTIFIER ::= { ciscoProducts 380 }		-- Cisco Wireless LAN Access Point 350 series 
ciscoDPA7610 OBJECT IDENTIFIER ::= { ciscoProducts 381 }	-- The Cisco Digital PBX Adapter (DPA) enables the integration of Cisco Call Manager with Octel voice mail systems.
cisco828	OBJECT IDENTIFIER ::= { ciscoProducts 382 }	-- Cisco 800 platform with 1 Ethernet, 1 G.991.2 (G.shdsl) Interface, data only model
cisco806	OBJECT IDENTIFIER ::= { ciscoProducts 384 }	-- Cisco SOHO (Small Office Home Office) router with 4 hubbed 10BaseT Ethernet LAN interfaces and 1 10BaseT Ethernet WAN interface
cisco12416	OBJECT IDENTIFIER ::= { ciscoProducts 385 }	-- Cisco 12000 platform with 16 slots and 10G fabric card 
cat2948gL3Dc    OBJECT IDENTIFIER ::= { ciscoProducts 386 }     -- A fixed-configuration Layer 3 Ethernet switch featuring IP, IPX, and IP mulitcast with 48 10/100BaseTX ports using DC power
cat4908gL3Dc    OBJECT IDENTIFIER ::= { ciscoProducts 387 }     -- A fixed-configuration L3 Ethernet switch featuring IP,IPX and IP multicast with 8 GBIC ports using DC power
cisco12406      OBJECT IDENTIFIER ::= { ciscoProducts 388 }     -- Cisco 12400 platform with 6 slots
ciscoPIXFirewall506	OBJECT IDENTIFIER ::= { ciscoProducts 389 }	-- Cisco PIX Firewall 506
ciscoPIXFirewall515	OBJECT IDENTIFIER ::= { ciscoProducts 390 }	-- Cisco PIX Firewall 515
ciscoPIXFirewall520	OBJECT IDENTIFIER ::= { ciscoProducts 391 }	-- Cisco PIX Firewall 520
ciscoPIXFirewall525	OBJECT IDENTIFIER ::= { ciscoProducts 392 }	-- Cisco PIX Firewall 525
ciscoPIXFirewall535	OBJECT IDENTIFIER ::= { ciscoProducts 393 }	-- Cisco PIX Firewall 535
cisco12410		OBJECT IDENTIFIER ::= { ciscoProducts 394 }	-- Cisco 12410 platform with 10 slots
cisco811		OBJECT IDENTIFIER ::= { ciscoProducts 395 }	-- ISDN router for Japan with 1 10BaseT Ethernet port, 1 ISDN BRI(Basic Rate Interface) U, integrated DSU(Data Service Unit)
cisco813		OBJECT IDENTIFIER ::= { ciscoProducts 396 }	-- ISDN router forJapan with 10 BaseT 4 ports hub , 1 ISDN BRI(Basic Rate Interface) U, integrated DSU(Data Service Unit) and 2 RJ-11
cisco10720		OBJECT IDENTIFIER ::= { ciscoProducts 397 }	-- IP + Optical Access Router
ciscoMWR1900		OBJECT IDENTIFIER ::= { ciscoProducts 398 }	-- The Mobile Wireless router is a router targeted at application in a cell site Base Transciever Station (BTS) providing T1/E1 backhaul connections to the aggregation node in Radio Access Networks (RAN)
cisco4224		OBJECT IDENTIFIER ::= { ciscoProducts 399 }	-- A standalone 24 port powered Ethernet switch, router and voice gateway
ciscoWSC6513		OBJECT IDENTIFIER ::= { ciscoProducts 400 }	-- Catalyst 6000 series chassis with 13 slots 
cisco7603		OBJECT IDENTIFIER ::= { ciscoProducts 401 }	-- Cisco Optical Services Router 7600 Series Chassis with 3 slots 
cisco7606		OBJECT IDENTIFIER ::= { ciscoProducts 402 }	-- Cisco Optical Services Router 7600 Series Chassis with 6 slots 
cisco7401ASR		OBJECT IDENTIFIER ::= { ciscoProducts 403 }	-- Cisco 7400 platform, ASR series with 1 slot 
ciscoVG248		OBJECT IDENTIFIER ::= { ciscoProducts 404 }	-- Cisco VoIP Voice Gateway for connecting analog telephones fax machines to a Cisco Call Manager based system 
ciscoHSE		OBJECT IDENTIFIER ::= { ciscoProducts 405 }	-- Cisco Hosting Solution Engine 1105 manages Cisco powered data centers and Points of Presence with routers, switches, server load balancers, firewalls, intrusion detection systems and other layer 4-7 content delivery products
ciscoONS15540ESP	OBJECT IDENTIFIER ::= { ciscoProducts 406 }	-- Cisco ONS 15540 Extended Services Platform
ciscoSN5420		OBJECT IDENTIFIER ::= { ciscoProducts 407 }	-- SRBU Storage Router 1 Fiber Channel port, 1 Gigabit Ethernet port 
ciscoCe507		OBJECT IDENTIFIER ::= { ciscoProducts 409 }	-- Cisco Content Engine Model 507
ciscoCe560		OBJECT IDENTIFIER ::= { ciscoProducts 410 }	-- Cisco Content Engine Model 560
ciscoCe590		OBJECT IDENTIFIER ::= { ciscoProducts 411 }	-- Cisco Content Engine Model 590
ciscoCe7320		OBJECT IDENTIFIER ::= { ciscoProducts 412 }	-- Cisco Content Engine Model 7320
cisco2691		OBJECT IDENTIFIER ::= { ciscoProducts 413 }	-- One Network Module slot, three WIC slot, two Fast Ethernet port MARS router 
cisco3725		OBJECT IDENTIFIER ::= { ciscoProducts 414 }	-- Two Network Module slot, three WIC slot, two Fast Ethernet port MARS router 
cisco1760		OBJECT IDENTIFIER ::= { ciscoProducts 416 }	-- Analog/digital voice capable, 19" rack-mount (1RU) Cisco 1700 platform with 2 WIC/VIC slots and 2 VIC-only slots 
ciscoPIXFirewall501	OBJECT IDENTIFIER ::= { ciscoProducts 417 }	-- Cisco PIX Firewall 501
cisco2610M		OBJECT IDENTIFIER ::= { ciscoProducts 418 }	-- c2600M with 1 integrated ethernet interface
cisco2611M		OBJECT IDENTIFIER ::= { ciscoProducts 419 }	-- c2600M with 2 integrated ethernet interfaces
cisco12404		OBJECT IDENTIFIER ::= { ciscoProducts 423 }	-- Cisco 12400 platform with 4 slots
cisco9004		OBJECT IDENTIFIER ::= { ciscoProducts 424 }	-- Cisco 9000 Chassis
cisco3631Co		OBJECT IDENTIFIER ::= { ciscoProducts 425 }	-- Two Network Module Slot , two WIC slot, one Fast Ethernet port MARS router 
catalyst295012G		OBJECT IDENTIFIER ::= { ciscoProducts 427 }	-- Cisco Catalyst c2950 switch with 12 10/100 BaseTX ports and 2 GBIC (Gigabit Interface Converter) slots (WS-c2950g-12) 
catalyst295024G		OBJECT IDENTIFIER ::= { ciscoProducts 428 }	-- Cisco Catalyst c2950 switch with 24 10/100 BaseTX ports and 2 GBIC (Gigabit Interface Converter) slots (WS-c2950g-12)
catalyst295048G		OBJECT IDENTIFIER ::= { ciscoProducts 429 }	-- isco Catalyst c2950 switch with 48 10/100 BaseTX ports and 2 GBIC (Gigabit Interface Converter) slots (WS-c2950g-12)
catalyst295024S		OBJECT IDENTIFIER ::= { ciscoProducts 430 }	-- Cisco Catalyst c2950 switch with 24 10/100 BaseSX ports (Single Mode) and 2 GBIC (Gigabit Interface Converter) slots (WS-c2950g-12)
catalyst355012G		OBJECT IDENTIFIER ::= { ciscoProducts 431 }	-- 10 Gig (GBIC) + 2 10/100/1000baseT ports, fixed configuration layer 2/3 Ethernet switch 
ciscoCE507AV		OBJECT IDENTIFIER ::= { ciscoProducts 432 }	-- Cisco Content Engine Model 507-AV
ciscoCE560AV		OBJECT IDENTIFIER ::= { ciscoProducts 433 }	-- Cisco Content Engine Model 560-AV
ciscoIE2105		OBJECT IDENTIFIER ::= { ciscoProducts 434 }	-- The Cisco Intelligence Engine 2100 series is a new form of network device that provides intelligent network interface to applications and users
ciscoMGX8850Pxm1E	OBJECT IDENTIFIER ::= { ciscoProducts 435 }	-- PXM1E Controller based 32 full-height slot MGX8850 
cisco3745		OBJECT IDENTIFIER ::= { ciscoProducts 436 }	-- 3700 family four slot modular router 
cisco10005		OBJECT IDENTIFIER ::= { ciscoProducts 437 }	-- Cisco 10000 platform with 7 slots
cisco10008		OBJECT IDENTIFIER ::= { ciscoProducts 438 }	-- Cisco 10000 platform with 10 slots 
cisco7304		OBJECT IDENTIFIER ::= { ciscoProducts 439 }	-- Cisco 7304 Chassis
ciscoRpmXf		OBJECT IDENTIFIER ::= { ciscoProducts 440 }	-- Chassis for RPM-XF router module 
cisco1721		OBJECT IDENTIFIER ::= { ciscoProducts 444 }	-- Enhanced 1720 with support for onboard Fast Ethernet and 2 WAN Interface cards and optional hardware encryption module 
cisco827H		OBJECT IDENTIFIER ::= { ciscoProducts 446 }	-- Cisco 800 platform with 4-port 10Base-T Ethernet, and 1 ADSL over POTS Interface, data only model 
cat4006			OBJECT IDENTIFIER ::= { ciscoProducts 448 }	-- Catalyst 4000 with 6 slots (WS-C4006)
ciscoWSC6503		OBJECT IDENTIFIER ::= { ciscoProducts 449 }	-- Catalyst 6000 series chassis with 3 slots 
ciscoPIXFirewall506E	OBJECT IDENTIFIER ::= { ciscoProducts 450 }	-- Cisco PIX Firewall 506E 
ciscoPIXFirewall515E	OBJECT IDENTIFIER ::= { ciscoProducts 451 }	-- Cisco PIX Firewall 515E
cat355024Dc		OBJECT IDENTIFIER ::= { ciscoProducts 452 }	-- Catalyst 3550 24 10/100Base-Tx ports + 2 Gig uplinks fixed configuration Layer 2/Layer 3 Ethernet Switch with DC power 
cat355024Mmf		OBJECT IDENTIFIER ::= { ciscoProducts 453 }	-- Catalyst 3550 24 10/100Mbps Multimode Fiber ports + 2 Gig uplinks fixed configuration Layer 2/Layer 3 Ethernet Switch
ciscoCE2636		OBJECT IDENTIFIER ::= { ciscoProducts 454 }	-- Cisco Content Engine Module for 26xx and 36xx series platforms
ciscoDwCE		OBJECT IDENTIFIER ::= { ciscoProducts 455 }	-- Double Wide Cisco Content Engine Module for 26xx
cisco7750Mrp300		OBJECT IDENTIFIER ::= { ciscoProducts 456 }	-- Cisco ICS 7750 Multiservice Route Processor 300 
ciscoRPMPR              OBJECT IDENTIFIER ::= { ciscoProducts 457 }      -- For RPM-PR router blade in MGX series switch
cisco14MGX8830Pxm1E     OBJECT IDENTIFIER ::= { ciscoProducts 458 }     -- PXM1E Controller based 14 slot MGX8830 
ciscoWlse               OBJECT IDENTIFIER ::= { ciscoProducts 459 }     -- Wireless LAN Solution Engine 
cisco6400UAC            OBJECT IDENTIFIER ::= { ciscoProducts 464 }     -- Cisco 6400 Universal Access Concentrator
ciscoAIRAP1200		OBJECT IDENTIFIER ::= { ciscoProducts 474 }	-- 1200 series WLAN Access Point with 1 10/100TX port, 1 CardBus slot, 1 Mini PCI slot
ciscoSN5428		OBJECT IDENTIFIER ::= { ciscoProducts 475 }	-- Storage Networking 5428 storage router with 2 SFP (Small Form  Factor Pluggable) GBIC Gigabit Ethernet ports and 8 SFP GBIC Fibre Channel ports 
cisco2610XM             OBJECT IDENTIFIER ::= { ciscoProducts 466 }     -- Cisco c2610XM platform 1 integrated fast ethernet interface with SDRAM
cisco2611XM             OBJECT IDENTIFIER ::= { ciscoProducts 467 }     -- Cisco c2611XM platform 2 integrated fast ethernet interfaces with SDRAM
cisco2620XM             OBJECT IDENTIFIER ::= { ciscoProducts 468 }     -- Cisco c2620XM platform 1 integrated fast ethernet interface with SDRAM
cisco2621XM             OBJECT IDENTIFIER ::= { ciscoProducts 469 }     -- Cisco c2621XM platform 2 integrated fast ethernet interfaces with SDRAM
cisco2650XM             OBJECT IDENTIFIER ::= { ciscoProducts 470 }     -- Cisco c2650XM platform 1 integrated fast ethernet interface with SDRAM
cisco2651XM             OBJECT IDENTIFIER ::= { ciscoProducts 471 }     -- Cisco c2651XM platform 2 integrated fast ethernet interfaces with SDRAM
catalyst295024GDC	OBJECT IDENTIFIER ::= { ciscoProducts 472 }	-- Cisco Catalyst c2950 switch with 24 10/100 BaseTX ports and 2 GBIC (Gigabit Interface Converter) slots and DC power(WS-c2950G-24-DC)
cisco7301		OBJECT IDENTIFIER ::= { ciscoProducts 476 }	-- Cisco 7300 platform, 1 Rack Unit (RU) application specific router with 1 slot 
cisco3250		OBJECT IDENTIFIER ::= { ciscoProducts 479 }	-- cisco 3250 mobile Router
catalyst295024SX 	OBJECT IDENTIFIER ::= { ciscoProducts 480 }	-- Cisco Catalyst c2950 switch with 24 10/100 BaseTX ports and 2 fixed 1000Base Multimode fiber (SX) ports 
ciscoONS15540ESPx	OBJECT IDENTIFIER ::= { ciscoProducts 481 }	-- Cisco ONS 15540 Extended Services Platform with external optical patch system
catalyst295024LRESt	OBJECT IDENTIFIER ::= { ciscoProducts 482 }	-- Cisco Catalyst c2950 switch with 24 10BaseS VDSL Ports and 2 ST ( SFP or 10/100/1000 Base T) (WS-C2950ST-24-LRE)
catalyst29508LRESt	OBJECT IDENTIFIER ::= { ciscoProducts 483 }	-- Cisco Catalyst c2950 switch with 8 10BaseS VDSL Ports and 2 ST (SFP or 10/100/1000 Base T) (WS-C2950ST-8-LRE)
catalyst295024LREG	OBJECT IDENTIFIER ::= { ciscoProducts 484 }	-- Cisco Catalyst c2950 switch with 24 10BaseS VDSL Ports and 2 GBIC ( Gigabit Interface Converter ) slots (WS-C2950G-24-LRE)
catalyst355024PWR	OBJECT IDENTIFIER ::= { ciscoProducts 485 } 	-- Catalyst 3550 24 10/100 ports with inline power and 2 Gig uplinks fixed configuration Layer 2/Layer 3 Ethernet Switch 
ciscoCDM4630		OBJECT IDENTIFIER ::= { ciscoProducts 486 }	-- Cisco Content Distribution Manager Model 4630
ciscoCDM4650		OBJECT IDENTIFIER ::= { ciscoProducts 487 }	-- Cisco Content Distribution Manager Model 4650
catalyst2955T12		OBJECT IDENTIFIER ::= { ciscoProducts 488 }	-- Cisco Catalyst c2955 Industrial switch with 12 10/100 BaseTX ports and 2 10/100/1000 Base-TX ports
catalyst2955C12		OBJECT IDENTIFIER ::= { ciscoProducts 489 }	-- Cisco Catalyst c2955 Industrial switch with 12 10/100 Base TX ports and 2 100 Base-FX ports
ciscoCE508		OBJECT IDENTIFIER ::= { ciscoProducts 490 }	-- Cisco Content Engine Model 508
ciscoCE565		OBJECT IDENTIFIER ::= { ciscoProducts 491 }	-- Cisco Content Engine Model 565
ciscoCE7325		OBJECT IDENTIFIER ::= { ciscoProducts 492 }	-- Cisco Content Engine Model 7325
ciscoONS15454		OBJECT IDENTIFIER ::= { ciscoProducts 493 }	-- Cisco ONS 15454 Platform
ciscoONS15327		OBJECT IDENTIFIER ::= { ciscoProducts 494 }	-- Cisco ONS 15327 Platform
cisco837		OBJECT IDENTIFIER ::= { ciscoProducts 495 }	-- Cisco 837 platform with 4-port 10/100 Base-T Ethernet Switch,1 ADSL over POTS interface,data only model, hardware encryption 
ciscoSOHO97             OBJECT IDENTIFIER ::= { ciscoProducts 496 }     -- SOHO (Small Office Home Office) Router with 4-port 10/100 Base-T Ethernet Switch,1 ADSL over POTS interface,data only model 
cisco831                OBJECT IDENTIFIER ::= { ciscoProducts 497 }     -- Cisco 831 platform with 4-port 10/100 Base-T Ethernet Switch, 1 10Base-T Ethernet WAN interface, hardware encryption 
ciscoSOHO91		OBJECT IDENTIFIER ::= { ciscoProducts 498 }     -- SOHO (Small Office Home Office)Router with 4-port 10/100 Base-T Ethernet Switch, 1 10Base-T Ethernet WAN interface 
cisco836                OBJECT IDENTIFIER ::= { ciscoProducts 499 }     -- Cisco 836 platform with 4-port 10/100 Base-T Ethernet Switch, 1 ADSL over ISDN interface,1 ISDN BRI S/T interface, hardware encryption 
ciscoSOHO96		OBJECT IDENTIFIER ::= { ciscoProducts 500 }     -- SOHO (Small Office Home Office)Router with 4-port 10/100 Base-T Ethernet Switch, 1 ADSL over ISDN interface, 1 ISDN BRI S/T interface 
cat4507			OBJECT IDENTIFIER ::= { ciscoProducts 501 }	-- Catalyst 4000 with 7 slots (WS-C4507)
cat4506			OBJECT IDENTIFIER ::= { ciscoProducts 502 }	-- Catalyst 4000 with 6 slots (WS-C4506) 
cat4503			OBJECT IDENTIFIER ::= { ciscoProducts 503 }	-- Catalyst 4000 with 3 slots (WS-C4503) 
ciscoCE7305		OBJECT IDENTIFIER ::= { ciscoProducts 504 }	-- Cisco Content Engine Model 7305 
ciscoCE510		OBJECT IDENTIFIER ::= { ciscoProducts 505 }	-- Cisco Content Engine Model 510 
ciscoAIRAP1100		OBJECT IDENTIFIER ::= { ciscoProducts 507 }	-- 1100 series WLAN Access Point with 1 10/100TX port, 1 IEEE 802.11 radio port.
catalyst2955S12		OBJECT IDENTIFIER ::= { ciscoProducts 508 }	-- Cisco Catalyst c2955 Industrial switch with 12 10/100 Base T ports and 2 100 Base-LX Single Mode Uplink ports 
cisco7609		OBJECT IDENTIFIER ::= { ciscoProducts 509 } -- Cisco 7600 Series Chassis with 9 slots 
catalyst375024		OBJECT IDENTIFIER ::= { ciscoProducts 511 } -- Catalyst 3750 24 10/100 ports + 2 Ethernet Gigabit SFP ports fixed configuration Layer 2/Layer 3 Ethernet  Stackable switch.
catalyst375048		OBJECT IDENTIFIER ::= { ciscoProducts 512 } -- Catalyst 3750 48 10/100 ports + 4 Ethernet Gigabit SFP ports fixed configuration Layer 2/Layer 3 Ethernet  Stackable switch.
catalyst375024TS	OBJECT IDENTIFIER ::= { ciscoProducts 513 } -- Catalyst 3750 24TS: 24 10/100/1000 ports + 4 Ethernet Gigabit SFP ports fixed configuration Layer 2/Layer 3 Ethernet  Stackable switch.
catalyst375024T		OBJECT IDENTIFIER ::= { ciscoProducts 514 } -- Catalyst 3750 24T: 24 10/100/1000 ports fixed configuration Layer 2/Layer 3 Ethernet  Stackable switch.
catalyst37xxStack	OBJECT IDENTIFIER ::= { ciscoProducts 516 } -- A stack of any catalyst37xx stack-able ethernet switches with unified identity (as a single unified switch), control and management.
ciscoGSS		OBJECT IDENTIFIER ::= { ciscoProducts 517 } -- The Global Site Selector (GSS) is a network appliance that performs global server load balancing for geographically dispersed server load balancers and caches using DNS resolution.
ciscoPrimaryGSSM	OBJECT IDENTIFIER ::= { ciscoProducts 518 } -- The Primary Global Site Selector Manager (GSSM) serves as the central management station for a Global Site Selector (GSS) Network.
ciscoStandbyGSSM	OBJECT IDENTIFIER ::= { ciscoProducts 519 } -- The Standby Global Site Selector Manager (GSSM) serves as the backup to the Primary GSSM in a Global Site Selector(GSS) Network.                                  
ciscoMWR1941DC		OBJECT IDENTIFIER ::= { ciscoProducts 520 } -- The Mobile Wireless Router (MWR-1941-DC) is a router with a universal power supply targeted at application in a cell site Base Transceiver Station (BTS) providing T1/E1 backhaul connections to the aggregation node in Radio Access Networks (RAN)
ciscoDSC9216K9		OBJECT IDENTIFIER ::= { ciscoProducts 521 }	-- DS-C9216-K9    -  MDS 9216 16-port 2Gbps FC + 1-slot Modular Switch
cat6500FirewallSm	OBJECT IDENTIFIER ::= { ciscoProducts 522 }	-- 	High performance firewall blade for Catalyst 6500 Series
ciscoCSM		OBJECT IDENTIFIER ::= { ciscoProducts 524 }	-- Cisco Content Switching Module (CSM) which load balancing internet traffic based on the layer 4 through layer 7 information in the content.
ciscoAIRAP1210		OBJECT IDENTIFIER ::= { ciscoProducts 525 }	-- 1200 series WLAN Access Point on Cisco IOS platform with 1 10/100TX port, 1 CardBus slot, 1 Mini PCI slot.
catalyst297024		OBJECT IDENTIFIER ::= { ciscoProducts 527 }	-- Catalyst 2970 24: 24 10/100/1000 ports fixed configuration Layer 2 Ethernet  switch 
cisco7613		OBJECT IDENTIFIER ::= { ciscoProducts 528 }	-- Cisco Internet router 7600 Series Chassis with 13 slots 
catalyst3750Ge12Sfp	OBJECT IDENTIFIER ::= { ciscoProducts 530 }	-- Cisco Catalyst c3750 switch with 12 SFP (Small Form  FactorPluggable) Gigabit Ethernet ports 
ciscoCR4430		OBJECT IDENTIFIER ::= { ciscoProducts 531 }	-- Cisco Content Router Model 4430 
ciscoCR4450		OBJECT IDENTIFIER ::= { ciscoProducts 532 }	-- Cisco Content Router Model 4450 
ciscoAIRBR1410		OBJECT IDENTIFIER ::= { ciscoProducts 533 }	-- 1410 Series Wireless LAN Bridge on Cisco IOS platform with 1 10/100Tx port and 1 5-GHz radio
ciscoWSC6509neba	OBJECT IDENTIFIER ::= { ciscoProducts 534 } -- Catalyst 6500 series chassis with 9 slots
catalyst4510		OBJECT IDENTIFIER ::= { ciscoProducts 537 } --	Catalyst 4000 with 10 slots (WS-C4510R) 
cisco1711		OBJECT IDENTIFIER ::= { ciscoProducts 538 } --	Enhanced security router with 4 FastEthernet switch ports, 1 Analog modem port, 1 FastEthernet port and a hardware encryption module 
cisco1712		OBJECT IDENTIFIER ::= { ciscoProducts 539 } --	Enhanced security router with 4 FastEthernet switch ports, 1 Basic Rate Interface(S/T)  data port, 1 FastEthernet port and a hardware encryption module. 
catalyst29408TT 	OBJECT IDENTIFIER ::= { ciscoProducts 540 } --	Catalyst 2940 L2 switch with 8 10/100 copper ports and 1 10/100/1000 copper uplink port.
catalyst29408TF 	OBJECT IDENTIFIER ::= { ciscoProducts 542 } --	Catalyst 2940 L2 switch with 8 10/100 copper ports, 1 100 FX Uplink port and 1 Gigabit SFP Module slot.
cisco2430Iad24Fxs	OBJECT IDENTIFIER ::= { ciscoProducts 545 } -- IAD2430 with 24FXS, 2FE 
cisco2431Iad8Fxs	OBJECT IDENTIFIER ::= { ciscoProducts 546 } -- IAD2431 with 8FXS, 2FE, 1T1/E1 
cisco2431Iad16Fxs	OBJECT IDENTIFIER ::= { ciscoProducts 547 } -- IAD2431 with 16FXS, 2FE, 1T1/E1 
cisco2431Iad1T1E1	OBJECT IDENTIFIER ::= { ciscoProducts 548 } -- IAD2431 with 2FE, 2T1/E1 
cisco2432Iad24Fxs	OBJECT IDENTIFIER ::= { ciscoProducts 549 } -- IAD2432 with 24FXS, 2FE, 2T1E1 
cisco1701ADSLBRI	OBJECT IDENTIFIER ::= { ciscoProducts 550 } -- Bacardi is a fixed configuration sku with ADSL WIC and ISDN BRI (S/T) or (S/T-V2) WIC 
catalyst2950St24LRE997	OBJECT IDENTIFIER ::= { ciscoProducts 551 } -- Catalyst2950 Long Reach Ethernet switch that confirms to ETSI 997 with 24 LRE interfaces, 2 10/100/1000 Small form factor copper interfaces and DC power supply(WS-C2950ST-24-LRE-997)
ciscoAirAp350IOS	OBJECT IDENTIFIER ::= { ciscoProducts 552 } -- Cisco Wireless LAN Access Point 350 series on IOS platform with 1 10/100TX port, 1 IEEE 802.11 radio port
cisco3220		OBJECT IDENTIFIER ::= { ciscoProducts 553 } -- 3220 - Mobile Access Router (MAR) 
cat6500SslSm		OBJECT IDENTIFIER ::= { ciscoProducts 554 } -- SSLSM is a High-Speed SSL Termination Engine for Catalyst 6000 family of platforms that terminates and accelarates Secure Socket Layer (SSL) transactions in Web server environement.
ciscoSIMSE		OBJECT IDENTIFIER ::= { ciscoProducts 555 } -- ciscoSIMSE is an appliance - CiscoWorks Security Information Management Solution Engine
ciscoESSE		OBJECT IDENTIFIER ::= { ciscoProducts 556 } -- Cisco Ethernet Subscriber Solution Engine
catalyst6kSup720	OBJECT IDENTIFIER ::= { ciscoProducts 557 } -- Catalyst 6500 Supervisor Module 720 CPU board that is treated as a standalone system by the NMS 
catalyst295048T		OBJECT IDENTIFIER ::= { ciscoProducts 559 } -- Cisco Catalyst c2950 switch with 48 10/100BaseT ports and 2 fixed 10/100/1000BaseT ports 
catalyst295048SX	OBJECT IDENTIFIER ::= { ciscoProducts 560 } -- Cisco Catalyst c2950 switch with 48 10/100BaseT ports and 2 fixed 1000Base Multimode fiber (SX) ports 
catalyst297024TS	OBJECT IDENTIFIER ::= { ciscoProducts 561 } -- Catalyst 2970 24TS: 24 10/100/1000 ports + 4 Ethernet Gigabit SFP ports fixed configuration Layer 2 Ethernet  switch 
ciscoAIRBR1300		OBJECT IDENTIFIER ::= { ciscoProducts 565 } -- Cisco Aironet 1300 Series Wireless Bridge with 1 10/100TX Ethernet port, 1 IEEE 802.11g radio port
catalyst375024ME	OBJECT IDENTIFIER ::= { ciscoProducts 574 } --	Metro Ethernet Catalyst 3750   24-10/100 + 2 SFP (Small Formfactor Pluggable) ports for downlinks and 2 SFP ES(Enhanched Service) ports for uplinks
catalyst4000NAM		OBJECT IDENTIFIER ::= { ciscoProducts 575 } --  Network analysis Module (NAM) for Catalyst 4000
cisco2811		OBJECT IDENTIFIER ::= { ciscoProducts 576 } --	Cisco 2800 series router with one Network Module slot, four HWIC slots, two fast etherenet and integrated VPN
cisco2821		OBJECT IDENTIFIER ::= { ciscoProducts 577 } --	Cisco 2800 series router with one Network Module slot, one EVM, four HWIC slots, two gigabit ethernet and intergrated VPN
cisco2851		OBJECT IDENTIFIER ::= { ciscoProducts 578 } --	Cisco 2800 series router with one double wide Network Module slot, one EVM, four HWIC slots, two gigabit ethernet and integrated VPN
cisco12006		OBJECT IDENTIFIER ::= { ciscoProducts 590 } --  Cisco 12000 platform with 6 slots
catalyst3750G16TD	OBJECT IDENTIFIER ::= { ciscoProducts 591 } --  Cisco Catalyst 3750 switch with 16 gigabit and one 10G ethernet port (WS-C3750G-16TD)
ciscoIGESM		OBJECT IDENTIFIER ::= { ciscoProducts 592 } --  Cisco Systems Intelligent Gigabit Ethernet Switch Module for IBM eServer BladeCenter (OS-CIGESM-18TT-E)
ciscoCCM		OBJECT IDENTIFIER ::= { ciscoProducts 593 }
ciscoCe511K9		OBJECT IDENTIFIER ::= { ciscoProducts 595 } --  Cisco Content Engine Model CE-511-K9
ciscoCe566K9		OBJECT IDENTIFIER ::= { ciscoProducts 596 } --  Cisco Content Engine Model CE-566-K9
ciscoMGX8880		OBJECT IDENTIFIER ::= { ciscoProducts 598 } --  Cisco MGX8880 switch with 32 half height slots
ciscoWsSvcWLAN1K9		OBJECT IDENTIFIER ::= { ciscoProducts 599 } --  Wireless LAN Module (WS-SVC-WLAN-1-K9) is a Komodo+ based line card for Cat6K family of platforms, which provides wireless domain services (WDS) for IEEE 802.11 wireless clients
ciscoCe7306K9		OBJECT IDENTIFIER ::= { ciscoProducts 600 } --  Cisco Content Engine Model CE-7306-K9
ciscoCe7326K9		OBJECT IDENTIFIER ::= { ciscoProducts 601 } --  Cisco Content Engine Model CE-7326-K9
ciscoBMGX8830Pxm45	OBJECT IDENTIFIER ::= { ciscoProducts 606 } --  PXM45 based Multiservice Switch (Model B) with 14 half height slots
ciscoBMGX8830Pxm1E	OBJECT IDENTIFIER ::= { ciscoProducts 607 } --  PXM1E based Multiservice Switch (Model B) with 14 half height slots
ciscoBMGX8850Pxm45	OBJECT IDENTIFIER ::= { ciscoProducts 608 } --  PXM45 based Multiservice Gigabit Switch (ModelB) with 32 half height slots
ciscoBMGX8850Pxm1E	OBJECT IDENTIFIER ::= { ciscoProducts 609 } --  PXM1E based Multiservice Gigabit Switch (ModelB) with 32 half height slots
ciscoNetworkRegistrar	OBJECT IDENTIFIER ::= { ciscoProducts 611 } --  Cisco Network Registrar (CNR) is a full-featured DNS/DHCP system that provides scalable naming and addressing services for enterprise and service provider networks.
ciscoCe501K9		OBJECT IDENTIFIER ::= { ciscoProducts 612 } --  Cisco Content Engine Model CE-501-K9
ciscoAIRAP1130		OBJECT IDENTIFIER ::= { ciscoProducts 618 } --	Cisco Aironet 1130 series WLAN Access Point with 1 10/100TX port, dual IEEE 802.11a and 802.11g  radio port
ciscoWsSvcMWAM1		OBJECT IDENTIFIER ::= { ciscoProducts 621 } --  Multiprocessor WAN Application Module (WS-SVC-MWAM-1) is a multipurpose blade built for the Cat6k platform
ciscoNMCUE		OBJECT IDENTIFIER ::= { ciscoProducts 622 } --	Cisco Unity Express network module (NM-CUE) 
ciscoAIMCUE		OBJECT IDENTIFIER ::= { ciscoProducts 623 } --	Cisco Unity Express advanced integration module (AIM-CUE) 
ciscoWLSE1130		OBJECT IDENTIFIER ::= { ciscoProducts 630 } --  Cisco WLAN Solution Engine (WLSE) 1130 monitors and configures a WLAN with Cisco WAP and Bridges
ciscoWLSE1030		OBJECT IDENTIFIER ::= { ciscoProducts 631 } --  Cisco WLSE Express 1030 is a  WLSE that monitors and configures a WLAN with Cisco WAP and Bridges with AAA functionality
ciscoHSE1140		OBJECT IDENTIFIER ::= { ciscoProducts 632 } --  Cisco Hosting Solution Engine 1140 manages Cisco powered data centers and Points of Presence with routers, switches, server load balancers, firewalls, intrusion detection systems and other layer 4-7 content delivery products
END
